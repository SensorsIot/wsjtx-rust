package WstxContact {
    private import ScalarValues::*;
    doc /* Canonical contract of the standard FT8 contact (issue #10, CL-010-01..04, -06,
         -10..-14 in WstxRequirements): standard messages Tx1-Tx6, the server-owned
         auto-sequencing state machine, manual DX Call/Grid entry, Rx/Tx audio frequency
         selection including waterfall pointer actions, Rx Frequency pane routing,
         worked-before determination, the contact log and operator display items.
         Declared coverage is target; nothing here is an execution result.

         Ownership. WstxArchitecture::QsoAndLogging owns contact identity, the sequence
         state, next-message choice, completion and the per-profile log. It never keys
         PTT, opens audio or touches a radio. It consumes the TARGET #9 slice B consumer
         contract in WstxTransmit (TransmitArming, TransmitRequest, TransmitOutcome,
         HaltTransmit, SetTune) over the qso.transmit -> transmit.contacts connection of
         WstxArchitecture::StationProcess. #9 slice B owns the armed state, halt, PTT
         and pending-request replacement; TransmitService alone holds the station's
         explicit transmit authority (WstxArchitecture::RadioAuthority) and plans starts
         with WstxTransmitSchedule::PlanTransmitStart. #9 slice B is delivered (WstxTransmit
         transmit owner); the engine consumes it in-process, so a station with transmit
         capability and a current CL-022 grant can arm through Enable Tx.
         A receive-only station (no transmit capability) can still select rows, prepare
         contacts and log; every transmit action is then refused with
         transmit_unavailable. Wire contract: ContactWire below. The browser
         renders server-confirmed state and sends requests; it runs no sequence timer,
         modem or QSO state machine (#10 functional description).

         Behaviour reference: WSJT-X 3.3.0-beta5 source (C:/WSJT/wsjtx-3.3.0-beta5-src;
         WstxProductScope::BehaviorBaseline v3.3.0-beta4 is unchanged for these
         functions). Cited as MW = widgets/mainwindow.cpp, DMR =
         DecodedMessageReaction.cpp, DOP = DecodeOutputPlan.cpp, PL = widgets/plotter.cpp,
         CFG = Configuration.cpp, LQ = widgets/logqso.cpp, ADQ = logbook/AdifQso.cpp,
         WB = logbook/WorkedBefore.cpp, HT = HelpText.cpp. Operator decisions: issue #10
         comment 6539901776 (2026-10-31), items D1..D11. Deliberate differences are
         marked DIFFERENT with their reason.

         FT4 (#11 CL-011-02..04) reuses this contract unchanged except the rules marked
         FT4-NOTE: 7.5 s periods (WstxTransmitSchedule::Ft4Schedule), Tx4 always RR73 (MW
         ~11227 forces m_send_RR73 in FT4), ADIF MODE MFSK with SUBMODE FT4 (ADQ
         to_adif), Tx offset upper bound 2916 Hz (Ft4WaveformContract). Which mode a
         contact uses and what a mode change does: StationOperatingMode, ContactMode
         and ModeChange below (#11 slice B). */

    // ---------------------------------------------------------------- messages
    enum def TxSlot { enum tx1; enum tx2; enum tx3; enum tx4; enum tx5; enum tx6; }
    enum def Tx4Form { enum rrr; enum rr73; }
    attribute def ReportRange {
        attribute minimumDb : Integer = -50;
        attribute maximumDb : Integer = 49;
        attribute manualDefaultDb : Integer = -15;
        doc /* Report value domain -50..+49 dB: DecodedText::report() clamps the decoded SNR
             (Decoder/decodedtext.cpp ~271) and widgets/mainwindow.ui rptSpinBox has
             min -50, max 49, value -15. Rendering is sign plus at least two digits,
             asprintf("%+2.2d") (MW genStdMsgs ~9738): -05, +03, +00, -15, +49.
             The value after selecting a decoded row is round-half-away-from-zero of its
             snr_db, clamped to this range; a row with null SNR, and manual DX entry,
             use the current report value, initially manualDefaultDb. Once the current Tx2
             or Tx3 text of the active contact was sent, selecting its partner again keeps
             the report (WstxContact::TxWatchdog). */
    }
    attribute def StandardMessageSet {
        attribute dxCall : String;
        attribute myCall : String;
        attribute myGrid4 : String;
        attribute reportDb : Integer;
        attribute tx4 : Tx4Form;
        attribute tx1Text : String;
        attribute tx2Text : String;
        attribute tx3Text : String;
        attribute tx4Text : String;
        attribute tx5Text : String;
        attribute tx6Text : String;
        assert constraint reportInRange { reportDb >= -50 and reportDb <= 49 }
        doc /* Generated by the server only (MW genStdMsgs ~9690, genCQMsg ~9594), with
             R = the rendered report and single blanks:
             Tx1 "DX MYCALL GRID4"; Tx2 "DX MYCALL R" e.g. "K1ABC HB9BLA -12";
             Tx3 "DX MYCALL R" with R prefixed by "R" and no blank, "K1ABC HB9BLA R-12";
             Tx4 "DX MYCALL RRR" or "DX MYCALL RR73" per tx4; Tx5 "DX MYCALL 73";
             Tx6 "CQ MYCALL GRID4". MYCALL and GRID4 come from the selected profile's
             callsign and the first four characters of its locator
             (WstxProfiles::Settings); without a profile callsign, or a locator for
             Tx1/Tx6, no message set is generated and transmit stays unavailable with
             that reason. Without a DX call only Tx6 exists. Directed CQ (CQ DX/nnn)
             is not offered.
             Nonstandard and compound calls (#24 S1b, CL-024-01; MW genStdMsgs ~9690-9850,
             77-bit branch): a call is standard when it matches Radio::is_standard_callsign
             (prefix [A-Z]{0,2}|[A-Z][0-9]|[0-9][A-Z], then a digit and at most 3
             letters, optionally /R or /P), else nonstandard (e.g. PJ4/K1ABC, DL/HB9BLA,
             YW18FIFA). With a nonstandard DX call and a standard MYCALL: Tx1
             "<DX> MYCALL GRID4", Tx2 "<DX> MYCALL R", Tx3 "<DX> MYCALL RR" (R prefixed by R),
             Tx4 "DX <MYCALL> RRR|RR73", Tx5 "DX <MYCALL> 73". With a nonstandard MYCALL
             and a standard DX call: Tx1 "<DX> MYCALL", Tx2 "DX <MYCALL> R", Tx3
             "DX <MYCALL> RR", Tx4 "<DX> MYCALL RRR|RR73", Tx5 "<DX> MYCALL 73", and Tx6
             "CQ MYCALL" (no grid; genCQMsg). Two nonstandard calls have no message set: such
             a DX call is refused invalid_call (make-qso.adoc: no QSO between two nonstandard
             calls). Every generated text must pack unaltered with
             WstxMessageEncode::PackMessage as the standard i3=1/2 or the nonstandard i3=4
             family; a DX call that does not is refused at entry. Contest forms belong to
             #24 S2. Regenerating after a report, DX call or tx4 change
             replaces Tx2-Tx4 (and Tx1/Tx5 on a DX-call change); operator-edited text
             of a slot is kept until the next regeneration and requires server
             validation through PackMessage before it can be chosen as next: it must
             pack unaltered as a standard i3=1/2, a nonstandard i3=4 or a free-text 0.0
             message (at most 13 characters of the free-text alphabet, WSJT-X Tx5 free
             text such as "TNX 73 GL", #24 S1b), else invalid_message. A free-text Tx5
             is sent like a 73: once sent in signoff the contact completes (logged only
             when it has a DX call).
             Tx4 default is rrr in FT8: m_send_RR73 starts false and is not saved
             (MW ~580, ~9661; Rr73Policy.cpp tx4AllowsRr73). FT4-NOTE: rr73, and
             always rr73 (MW send_rr73_for_tx4 ~9661 is true for FT4 whatever
             m_send_RR73; set_rr73_tx4 ~9676 forces it), see ToggleTx4Form. */
    }
    enum def SpecialActivity { enum none; enum na_vhf; enum eu_vhf; enum ww_digi; enum arrl_digi; enum field_day; enum rtty; enum hound; }
    attribute def GridExchangeContest {
        attribute activity : SpecialActivity;
        doc /* #24 S2a, CL-024-02 (WSJT-X 3.3.0-beta5 Settings > Advanced > Special operating
             activity; MW genCQMsg ~9610-9631, genStdMsgs ~9758-9760 sent=my_grid;
             DecodedMessageReaction.cpp ~533-547; make-qso.adoc Contest Messages). The
             operator chooses the station's activity with set_activity {activity}: none
             (default), na_vhf (NA VHF), ww_digi (WW Digi) or arrl_digi (ARRL Digi). It is
             a station setting of this boot (not saved; a restart starts with
             none) and applies to the next message generation; the current contact's
             Tx2-Tx4 and Tx6 are regenerated at once (a report or tx4 change still
             replaces only Tx2-Tx4). Station automation does not start while an activity
             other than none is set (WstxMcp, not_ready activity): it only observes. Like
             the auto_seq and call readiness, this is checked when a run starts; choosing
             an activity during a running automation run does not stop it (the operator
             chooses the contest before starting, and HALT or Stop ends a run). With an activity other than none:
             Tx6 is "CQ TEST MYCALL GRID4" (na_vhf, arrl_digi) or "CQ WW MYCALL GRID4"
             (ww_digi) when MYCALL is standard (a nonstandard MYCALL keeps "CQ MYCALL");
             the exchange is my grid instead of the report: Tx2 is the Tx1-Tx3 stem of
             StandardMessageSet plus GRID4 and Tx3 the stem plus "R GRID4" (e.g. "K1ABC
             HB9BLA JN47", "K1ABC HB9BLA R JN47"); Tx1, Tx4 and Tx5 are unchanged. A
             partner message to my call is classified (ContestReceivedKind): a grid
             without R as signalReport, a grid with R as rogerReport, everything else as
             in a standard QSO. So a caller's grid after my CQ selects Tx3 (rogerReport),
             a CQer's "R GRID" after my first message (Tx2 since Tx1 is disabled in contests, #24 S2b) moves to Tx4 (rogers), and RRR/RR73/73 end the
             contact as usual, which logs it (log on RRR/RR73/73, make-qso.adoc NIL
             guidance); report_sent and report_rcvd stay null and the received grid is the
             DX grid. Contest dupes are the existing worked-before indication of the
             call on this band and mode (WorkedBeforeQuery). The UDP Status special
             operation carries the WSJT-X SpecialOperatingActivity value: none 0, na_vhf 1,
             ww_digi 5, arrl_digi 8, field_day 3, rtty 4, hound 7 (HoundOperation), eu_vhf 2. Field Day and FT Roundup:
             ContestExchange (#24 S2b); EU VHF: EuVhfExchange (#99). In every contest activity
             (not none, not hound) except eu_vhf Tx1 is disabled
             as in WSJT-X (MW ~8190: "start QSO with Tx2"): a selection or entry that would
             start with Tx1 starts with Tx2, as with Skip Tx1. In eu_vhf Tx1 stays enabled
             (MW ~8203: "We're in EU_VHF mode: start QSO with Tx1"). */
    }
    attribute def ContestExchange {
        attribute exchange : String[0..1];
        attribute serial : Integer;
        doc /* #24 S2b2, CL-024-03 (WSJT-X 3.3.0-beta5 genCQMsg ~9620, genStdMsgs ~9741-9790,
             DecodedMessageReaction.cpp ~460-560, mainwindow guiUpdate ~8012-8017 and
             ~10542, logqso.cpp ~386-412, logbook.cpp ~92-110, AdifQso.cpp to_adif;
             Configuration.cpp Field_Day_Exchange / RTTY_Exchange). set_activity
             {activity:"field_day"|"rtty", exchange} chooses ARRL Field Day or FT/RTTY
             Roundup with the station's configured exchange; it is a boot setting like
             the activity (not saved). field_day: exchange "nC SECTION" (n 1-32 without
             a leading zero, C A-F, SECTION one of the 86 decoder sections, DX outside
             W/VE), e.g. "1A EMA". rtty: exchange a state/province/multiplier of the 171
             RTTY exchanges, e.g. "MA", a fixed four-digit number 0001-7999, or "DX" or "#"
             for a four-digit serial. Only ASCII is accepted. Upper case
             is folded and blank runs collapse; anything else, a missing exchange for these
             two, or an exchange for another activity is refused invalid_request field
             exchange. serial is the station's contest serial number: 1 at boot,
             incremented by one each time a contact is logged (DirectLog, completion or
             Log QSO of a contact not yet logged) while an activity other than none is set
             (MW ~10542), never reset by set_activity. set_activity also sets the activity of the
             current contact (its messages are regenerated and its log fields follow it).
             DIFFERENT from WSJT-X: a contest contact without exchange_sent or
             exchange_rcvd is still logged (logqso.cpp ~415 refuses it), and the RTTY RST of
             each side is replaced independently. UDP QSO Logged carries the exchanges as
             WstxRequirements::'CL-112-05' rebuilds them from the stored record.
             Messages (both calls must be standard calls; otherwise generation fails
             invalid_call, since WSJT-X would hash and alter the call): Tx6 "CQ FD MYCALL
             GRID4" / "CQ RU MYCALL GRID4"; the sent exchange is the Field Day exchange,
             or for rtty "5n9 X" with n=(report+36)/6 truncated toward zero and clamped to
             2..9 and X the configured exchange or, for DX/#, the serial as four digits;
             Tx2 is the StandardMessageSet Tx1-Tx3 stem plus the sent exchange and Tx3 the
             stem plus "R " plus it (e.g. "K1ABC HB9BLA 1A EMA", "K1ABC HB9BLA R 559
             0003"); Tx1, Tx4, Tx5 unchanged. FT4 TU; (MW ~9783): in rtty and FT4, when the
             operator (not automation) selects a row while fewer than 15 whole seconds
             have passed since the start of the period of the station's last transmission
             and fewer than 3 whole seconds since the last partner RR73 was counted (Qt
             secsTo), Tx3 is prefixed "TU; ".
             Received (ContestReceivedKind): a Field Day message to my call in field_day,
             or an RTTY Roundup message to my call in rtty (TU; ignored), is a
             signalReport without R and a rogerReport with R; in another activity it is
             other. Its last two words (e.g. "6A WI", "579 MA", "559 0013") are the
             contact's exchange_rcvd; exchange_sent is the last two words of Tx2 once a
             Tx2 or Tx3 is transmitted. report_sent/report_rcvd stay null.
             Log (DirectLog, AdifQso::to_adif): rtty RST_SENT/RST_RCVD are the first words
             (5n9) of exchange_sent/exchange_rcvd. exchange_sent: a two-word value whose
             second word is a positive number gives STX (that word), otherwise
             STX_STRING (the value). exchange_rcvd: a positive number second word gives
             SRX; otherwise field_day gives CONTEST_ID ARRL-FIELD-DAY, SRX_STRING (the
             value), CLASS (first word) and ARRL_SECT (second word); rtty gives STATE
             (second word); another activity SRX_STRING. Fields are written in the
             LogRecord order. */
    }
    attribute def EuVhfExchange {
        attribute serialMinimum : Integer = 1;
        attribute serialMaximum : Integer = 2047;
        attribute gridLength : Integer = 6;
        doc /* #99, CL-099-02 (WSJT-X 3.3.0-beta5 genCQMsg ~9619, genStdMsgs ~9774-9779,
             guiUpdate ~8008-8011 and ~8203-8207, ~3431 and ~10280 (6-character locator),
             ~10542 and ~10669 (serial, eu_vhf_type5_serial_max), DecodedMessageReaction.cpp
             ~501-565 and ~772-776, AdifQso.cpp to_adif ~87-124; packjt77 type 5:
             WstxMessageEncode::PackMessage). The EU VHF contest message: report, serial and
             6-character locator, both calls hashed.
             Choosing. set_activity {activity:"eu_vhf"} without an exchange (an exchange is
             refused invalid_request field exchange), FT8 and FT4, a boot setting like the
             other activities (not saved). It is refused profile_incomplete with field
             locator, the activity unchanged, while the selected profile's locator
             (WstxProfiles::Settings) has fewer than 6 characters (empty or 4: WSJT-X only
             warns, "EU VHF Contest messages require a 6-character locator"), and refused
             invalid_call with field callsign while the profile callsign has more than 11
             characters (a hashed slot holds no more; the profile admits 12). The serial is
             ContestExchange serial, the one station contest serial (1 at boot, +1 for each
             logged contact while a contest activity is set, never reset by set_activity);
             #98 replaces its source by the log (highest STX of the contest + 1) for rtty and
             eu_vhf alike.
             Messages. Tx6 "CQ TEST MYCALL GRID4" (a nonstandard MYCALL keeps "CQ MYCALL");
             Tx1, Tx4 and Tx5 are StandardMessageSet's, including its nonstandard and
             compound rules (#24 S1b), and Tx1 stays enabled (GridExchangeContest); Tx2
             "<DX> <MYCALL> 5nSSSS GRID6" and Tx3 "<DX> <MYCALL> R 5nSSSS GRID6" (e.g.
             "<K1ABC> <HB9BLA> 550001 JN37VL", "<K1ABC> <HB9BLA> R 550001 JN37VL"), with n =
             (report+36)/6 truncated toward zero and clamped to 2..9 (the report of
             ReportRange, as ContestExchange's 5n9), SSSS the serial as four digits and GRID6
             the first six characters of the profile locator (an 8-character locator sends
             its first six, JN37VL12 sends JN37VL). Both calls are hashed whatever their
             form, so each is 3-11 characters, and the message limit of 37 characters
             (PackMessage tooLong; WSJT-X has no longer message) bounds the pair: Tx3 is
             len(DX) + len(MYCALL) + 21 characters, so the two calls together have at most 16
             characters (e.g. HB9BLA with a DX call of at most 10, HB9BLA/P with at most 8).
             The pair is checked before a contact starts, so no contact starts whose Tx3
             cannot be packed: while eu_vhf is set, a selection (SelectDecodedRow, also from
             Call 1st and automation) or entry (EnterDxStation) whose DX call has more than 11
             characters or more than 16 together with my call is refused invalid_call (no
             field, as the other DX-call refusals), nothing changes, and Call 1st goes on to
             the next caller. set_activity eu_vhf with an active contact whose pair is too
             long is refused invalid_call with field dx_call, the activity unchanged.
             Every command that regenerates the active contact's messages (set_activity,
             set_report, set_tx4, a selection or entry of the same partner) is refused, and
             changes nothing, when its Tx2/Tx3 cannot be generated: out_of_range with field
             serial when the serial is outside 1..2047 (WSJT-X's spin box maximum; a station
             that logged 2047 contacts), profile_incomplete with field locator when the
             profile locator was changed to fewer than 6 characters after the choice, and
             invalid_call with field callsign when the profile callsign was changed so that it
             has more than 11 characters or the pair more than 16. A profile change alone
             regenerates nothing: the messages already generated stay until such a command,
             and a new selection or entry is refused the same way. Every
             generated text packs unaltered (PackMessage, family euVhf for Tx2/Tx3). An
             operator-edited Tx2 or Tx3 is accepted when it packs unaltered in any family,
             including euVhf. The accepted request teaches the hash table both calls
             (WstxOfflineDecode::HashResolution). The partner can resolve my hashed call only
             from a message that carries it in full (my CQ or Tx1): that is why Tx1 stays.
             Received (ContestReceivedKind in eu_vhf). An EU VHF message (decoded fields type
             vhf) counts as the partner's message to me when its 'to' h12 equals the 12-bit
             hash of my profile callsign and its 'from' h22 equals the 22-bit hash of the
             contact's DX call, decoded in the partner's period in the contact's mode (the
             AutoSequence counting rules otherwise); without R it is signalReport (Tx3 next,
             rogerReport), with R rogerReport (Tx4 next, rogers). A standard grid message to my
             call stays grid (Tx2 next, report), as WSJT-X (DMR ~534 excludes EU VHF from the
             grid-as-report rule); a standard report or R+report to my call is classified as
             without an activity; RRR, RR73 and 73 end the contact as usual. In every other
             activity an EU VHF message is other. A counted EU VHF message sets the contact's
             exchange_rcvd to its last two words ("590003 IO91NP", WSJT-X right(13)) and its
             dxGrid to the 6-character locator; exchange_sent is the last two words of Tx2 once
             a Tx2 or Tx3 is transmitted. report_sent/report_rcvd stay null.
             Selection. While eu_vhf is set an EU VHF row whose 'from' is a filled-in hash is
             selectable (SelectDecodedRow): dx call its 'from' text, dx grid its locator;
             addressed to me (its 'to' is my call) the first slot is tx3 without R and tx4
             with R, and its last two words become exchange_rcvd, as a selected RTTY Roundup
             or Field Day row addressed to me does and as WSJT-X stores the received exchange
             of an EU VHF message to my call (DMR ~772-776); otherwise tx1 (replying) and
             exchange_rcvd stays null. An unresolved 'from' is refused
             row_not_standard, as WSJT-X refuses a contest message with <...>. In another
             activity such a row is refused row_not_standard as before. Call 1st, the
             strategies and contest verdicts keep reading standard messages only: a caller's
             Tx1 grid is answered with Tx2.
             Log (DirectLog, LogRecord). STX is the last four digits of the first word of
             exchange_sent ("0001"), SRX those of exchange_rcvd (AdifQso mid(2)); RST_SENT and
             RST_RCVD are the two-digit RS 52..59 of those words, the RS actually exchanged
             ("55", "59"; operator 2026-11-09 on #99: "Log the exchanged 55/59"); GRIDSQUARE is the
             partner's 6-character locator; no STX_STRING or SRX_STRING. UDP Status special
             operation 2. DIFFERENT from WSJT-X: (1) set_activity is refused without a
             6-character locator (WSJT-X warns and then sends a message type 5 cannot
             carry); (2) a partner message counts by the two hashes against my call and the
             DX call, never by whatever call the table fills in, as HoundOperation (2);
             (3) RST_SENT/RST_RCVD log the RS that was exchanged, not the dB report WSJT-X
             writes; (4) the contest hint WSJT-X shows for an EU VHF message in another
             activity is not offered. */
    }
    attribute def HoundOperation {
        attribute foxHz : Integer;
        doc /* #24 S4b, CL-024-04: classic Fox/Hound as the Hound (WSJT-X 3.3.0-beta5
             HoundTransmissionPolicy.cpp planFoxReportReply/planClassicTxStart; MW hound_reply
             ~14896, readFromStdout Hound block ~7380-7420, guiUpdate Tx start ~7726-7790,
             clearDX ~9951, special-op setup ~11352, processMessage ~9143, guiUpdate HWD
             ~8317, Tx watchdog ~14664, on_actionFT4_triggered; DecodedMessageReaction.cpp
             ~250 and ~304; controls-functions-left.adoc). SuperFox stays excluded
             (the SuperFox exclusion of WstxModemDecode::AdvanceDecode; #24 S5 moved to #77 (phase two)); the station is never
             the Fox (S6 dropped).
             Choosing. set_activity {activity:"hound"} (no exchange) is a boot setting like
             the other activities, FT8 only: it is refused state_conflict while the station
             operating mode is FT4, and a change of the station mode to FT4 sets the
             activity back to none (MW on_actionFT4_triggered). Choosing hound sets Tx
             parity odd (Tx even/1st forced off: I always transmit in the second period),
             Hold Tx on, and moves a current contact's next slot to tx1 unless it is tx3.
             While hound is set: set_parity even is refused state_conflict; choose_next
             accepts only tx1 and tx3 (others state_conflict); Tx1 is never skipped (MW
             elide_tx1_not_allowed), and every request carries Tx1 or Tx3 only (MW ~7783).
             UDP Status special operation 7. Station automation does not start
             (not_ready activity) and Call 1st never applies (a Hound never calls CQ):
             Enable Tx without a contact that has a DX call is refused no_contact.
             Selection (SelectDecodedRow) of a row decoded in a period starting at second
             15 or 45 of the minute is refused state_conflict ("select a Fox at :00 or
             :30", MW ~9143); a row whose exchange is R plus a report is refused
             state_conflict ("hound ignores other hounds", DMR ~304); the selection never
             sets the Tx offset from the row (DMR ~330); its first slot is tx3 for a report
             to my call and tx1 otherwise. 0.1 DXpedition rows stay unselectable
             (row_not_standard), as before.
             Received rows replace AutoSequence while hound is set (MW calls auto_sequence
             only outside FT8 Hound): of an active contact, counted once, decoded in the
             period of the parity opposite to mine, a row is (a) the Fox's report: a
             standard message to my call from the DX call with a report without R, or a
             0.1 DXpedition message "X RR73; MYCALL <FOX> rr" whose report slot is my call
             and whose hashed call is the DX call (HashResolution hashdx10); (b) the Fox's
             RR73: a standard RR73 to my call from the DX call, or a 0.1 message whose RR73
             slot is my call and whose hashed call is the DX call. (b) completes the contact
             at once (Enable Tx off with cause contactCompleted, handed to the log as any
             completion, MW stopTx + logQSO); the next selection starts a new contact. (a)
             is FoxReportReply: foxHz := the row frequency rounded; nothing else while Tune
             is on; otherwise report_rcvd := the Fox's report, the contact's report := the
             row SNR (ReportRange, MW m_rptSent from the decode), Tx3 regenerated and next,
             state rogerReport, the Tx offset := foxHz when it is a valid Tx offset, the
             reply becomes pending and the reply timeout is 11 T/R periods (165 s) from now.
             ClassicTxStart, once for each new period the engine plans a request for (the
             request's tx_offset_hz): a Tx1 with a Tx offset below 999 Hz moves to a
             uniformly random offset 1000..2998 Hz (QRandomGenerator bounded(1000,2999));
             a Tx3 after a sent reply moves to foxHz+300 when foxHz <= 600, else foxHz-300.
             A pending reply becomes sent when its transmission starts. So the first Tx3
             after a Fox report goes out on the Fox's frequency and a repeat without a new
             report on Fox +-300 Hz; a repeated Fox report returns it to the Fox's
             frequency.
             Timeouts: when the reply timeout passes Enable Tx is turned off (cause
             txWatchdog, the slot stays tx3; MW stopWRTimeout); the operator turning Enable
             Tx on or off ends the reply timeout (MW on_autoButton_clicked stopWRTimer.stop); while Tx1 is next and
             300 s have passed since the last accepted start (Enable Tx on, or a start action
             of StartActions, a run's own included; reset_repetitions does not restart the
             300 s: CL-111-10) the transmit state is
             turned off (cause txWatchdog; MW Hound watchdog HWD); after the station's Tx
             watchdog expires the next slot returns to tx1 (MW ~14664). A completed contact
             leaves the station ready to call the next Fox with Tx1.
             DIFFERENT from WSJT-X: (1) a Fox report never turns Enable Tx on (WSJT-X
             auto_tx_mode(true)): only the operator arms (CL-022, #10 safety rule); (2) the
             RR73 that completes must come from the DX call (standard) or carry the DX
             call's hash (0.1); WSJT-X completes on any RR73 to my call, so another station's
             RR73 would log my contact with the Fox; likewise a 0.1 report to my call is
             answered only when its hashed call is the DX call (WSJT-X answers it whatever
             the hashed call, also an unresolved <...>); (3) the decoder keeps the full 200-3000
             Hz range (WSJT-X decodes only below 1000 Hz unless Rx All is checked), so
             Band Activity also shows other Hounds; (4) the decision for a period is taken
             when its request is planned (after the previous own transmission started),
             not at its key-down; a Fox report decoded before key-down still sets the
             Fox's frequency for it, and no decision is taken while Tune is on; (5) the
             reply state and the reply timeout belong to one contact: a completion or a new
             contact ends them (WSJT-X's stopWRTimer keeps running and can turn off Enable
             Tx for the next Fox). */
    }
    action def ToggleTx4Form {
        doc /* D7 adopted (MW on_txrb4_doubleClicked ~9047): switches tx4 between rrr
             and rr73 for the current contact and regenerates Tx4. Applies to the next
             transmission, never to one whose audio has started. FT4-NOTE: an FT4
             contact keeps rr73; set_tx4 rrr on it is refused out_of_range with field
             form and changes nothing (DIFFERENT from WSJT-X, which silently keeps RR73:
             a refusal never looks like an accepted change). */
    }
    action def OverrideReport {
        in requestedReportDb : Integer;
        doc /* D7 adopted (rptSpinBox, MW genStdMsgs): the operator sets the report sent
             in Tx2/Tx3; -50..+49 accepted, other values refused with the range. The
             override applies to the next transmission. A later row selection for a
             new partner sets the report from that row again (DMR appendReactedTail
             ~388-400). RST_SENT logs the report actually transmitted last. */
    }
    action def ToggleTx1Skip {
        doc /* D7 adopted (MW on_txrb1_doubleClicked ~9010 toggle_tx1_enabled_preference):
             with Tx1 skipped, a reply to a CQ or to a station not addressed to me starts
             with Tx2 and state report instead of Tx1/replying (DMR ~696-704), and
             choosing Tx1 as next selects Tx2 (MW ~8989). The Tx1 text is kept.
             Station-session preference, initially not skipped (mainwindow_settings
             tx1State default true); not part of the saved profile schema. */
    }

    // ---------------------------------------------------------------- contact
    enum def ContactOrigin { enum decodedRow; enum manualEntry; enum ownCq; }
    enum def SequenceStateName {
        enum idle; enum calling; enum replying; enum report; enum rogerReport;
        enum rogers; enum signoff; enum completed; enum cancelled;
    }
    attribute def Contact {
        attribute contactId : String;
        attribute origin : ContactOrigin;
        attribute dxCall : String[0..1];
        attribute dxGrid : String[0..1];
        attribute reportSentDb : Integer[0..1];
        attribute reportReceivedDb : Integer[0..1];
        attribute rxOffsetHz : Integer;
        attribute txOffsetHz : Integer;
        attribute holdTx : Boolean;
        attribute txParity : WstxTransmit::PeriodParity;
        attribute nextSlot : TxSlot;
        attribute lastTransmittedText : String[0..1];
        attribute sequenceState : SequenceStateName;
        attribute armState : WstxTransmit::ArmState;
        attribute mode : WstxOfflineDecode::Mode;
        attribute autoSequence : Boolean;
        attribute callFirst : Boolean;
        attribute startUtc : String[0..1];
        attribute endUtc : String[0..1];
        attribute saved : Boolean;
        doc /* Server-owned. contactId is a fresh lowercase UUID v4 created when a
             partner is prepared (row selection or manual entry) and kept through
             retries, reconnect, restart recovery and the log record
             (APP_WSTXRUST_CONTACT_ID). One active contact per station profile.
             A different partner while a contact is active (state replying..signoff)
             requires the explicit ChangeContact operation; a late row or stale request
             cannot change the transmitting partner. dxGrid is 4 or 6 Maidenhead
             characters or absent. nextSlot and lastTransmittedText are distinct and
             both shown. Reconnect loads this snapshot; it replays no arm, tune,
             next-message or transmit request. Another profile never inherits it.
             autoSequence is on at a profile's first start and afterwards as saved
             (CL-110-01, QsoSettingsFile); the operator can switch it off, and off means
             received messages never change nextSlot. callFirst (WSJT-X Call 1st /
             "CQ: First") is on at a profile's first start and afterwards as saved
             (CL-110-01, QsoSettingsFile), see CallFirst. Relation to WSJT-X 3.3.0-beta
             (widgets/mainwindow_settings.cpp). Followed: both settings are kept across
             starts, as WSJT-X keeps AutoSeq (group Common) and RespondCQ (group
             MainWindow) with its configuration. Deliberate difference: both are on when
             nothing is saved, where WSJT-X starts with AutoSeq false and RespondCQ None.
             Own choice: the value is saved with each accepted change, where WSJT-X
             writes its settings in writeSettings (at exit and at configuration changes),
             so that a change can be lost there when the program ends abnormally.
             armState is the
             read view of #9's TransmitArming, never armed by selection, entry, reconnect or startup (#10 CL-010-01,
             TransmitSafetyPolicy armedOnStartup=false). mode: ContactMode. */
    }
    attribute def QsoSettingsFile {
        attribute schemaVersion : Integer = 1;
        attribute profileId : String;
        attribute autoSeq : Boolean;
        attribute callFirst : Boolean;
        attribute bytesMax : Integer = 256;
        doc /* CL-110-01. The saved Auto Seq and Call 1st of one profile: qso-settings.json
             in the selected profile directory, exactly {schema_version, profile_id,
             auto_seq, call_first}: schema_version the integer 1, profile_id the profile's
             UUID, auto_seq and call_first JSON booleans; at most bytesMax bytes; written
             atomically like udp.json (WstxUdp::UdpConfiguration) under the profile's own
             lock (WstxProfiles), so that saving it does not advance the profile revision.
             A missing file leaves both at the start values of Contact. So does a file
             that is unreadable, larger than bytesMax bytes, not this exact object, of
             another schema_version or of another profile_id: the station starts as
             usual, no error is displayed, and the next accepted set_auto_seq or
             set_call_first replaces the file with a valid one. No other setting of
             ContactSnapshot settings is in the file.
             The contact station reads the file once, when it is created at the station
             start, and the ContactCommand path writes both values before the engine
             takes the changed one and before the receipt; a failed write refuses the
             command storage_unavailable (ContactRefusal) and changes nothing. */
    }
    calc def StationOperatingMode {
        in liveDecodingMode : WstxOfflineDecode::Mode[0..1];
        in selectionMode : WstxOfflineDecode::Mode;
        return mode : WstxOfflineDecode::Mode;
        doc /* #11 CL-011-02. The station's operating mode is the mode of whichever came
             last: the last started ft4|ft8 live decoding job (WstxOperatingReceive
             receive start, including the former Next receive mode control) or the last
             admitted operating selection (its requested mode, from admission on, even
             if the restart later fails); FT8 at a fresh boot. It persists across a
             receive stop and a spectrum-only job (review repair 2026-11-01: an FT4
             contact is not cancelled by stopping receive). An operating selection with
             action band keeps it: the band's entry is resolved in the station's
             operating mode, not in WireSelection's last mode (WSJT-X keeps the mode on
             a band change). FT4 is selected per station through the existing
             operating selection (action mode ft4, which retunes the dial to the FT4
             entry and restarts the live job in FT4) or the existing receive start;
             there is no second mode control, browser, rig-control, log or transmit
             authority for FT4: the #9 transmit panel's mode is a read-only display of
             this mode, its Tx offset input and the contact Tx input are bounded by the
             mode's domain (2916 Hz FT4, 2950 Hz FT8), both following station.tick. It
             sets the mode of a manually entered contact and of an own CQ, the Tx offset
             domain (FrequencyControls), station.tick period_ms (7500 FT4, 15000 FT8)
             and WstxTransmit::StationModeGate. */
    }
    attribute def ContactMode {
        doc /* #11 CL-011-03. A contact's mode is fixed when it is prepared: the selected
             row's mode (the live job that decoded it) or StationOperatingMode for
             manual entry and own CQ. All of its rules use that mode: messages
             (FT4-NOTE Tx4), TransmitSubmission requests (mode carried in every
             WstxTransmit::TransmitRequest, so #9 plans Ft4Schedule or Ft8Schedule and
             renders that waveform), period parity, TIME_ON/TIME_OFF period lengths, log
             MODE/SUBMODE and worked-before mode. Only decoded rows of the contact's
             mode count as received messages or for the 50 Hz rule; a row of the other
             mode never changes the sequence (cross-mode isolation). Re-preparing the
             same DX call in the other mode is a different contact (new contactId,
             ChangeContact rules). Each station process owns its own engine, transmit
             owner and contacts.adi, so simultaneous FT4 and FT8 stations share no
             contact, arm or log state. */
    }
    action def ModeChange {
        doc /* #11 CL-011-04. When StationOperatingMode differs from the mode of a contact
             in calling, replying, report, rogerReport, rogers or signoff, the engine
             (at its next step or command: POST /receive/start, /receive/stop and an
             admitted /receive/select run one synchronous contact step before their
             202 reply, otherwise at most one 50 ms step later) turns Enable
             Tx off through #9 (TransmitArming disarm, DisarmCause modeChanged: no
             unkeyed request of the old mode remains) and cancels the contact as
             CancelContact (calling -> idle; replying..signoff -> cancelled, DX call and
             Tx1-Tx5 cleared, Tx6 next). A completed contact keeps its fields and its
             log record keeps its own mode (DirectLog); idle and cancelled contacts are
             unchanged. The Tx offset is clamped into the new mode's domain (an FT8
             2917..2950 Hz offset becomes 2916 Hz in FT4). Enable Tx afterwards starts a
             fresh own CQ in the new mode. DIFFERENT from WSJT-X, which keeps the DX
             call and Enable Tx across a mode change: a contact's messages, periods and
             log mode belong to one mode, so no contact or arm continues across modes.
             As WSJT-X (MW updateModeControlLock disables the mode controls while
             transmitting), an operating selection with action mode is refused busy,
             after the profile/revision checks and before any effect, while #9 reports
             PTT keyed, a transmission or Tune. Independently of the contact step, the
             #9 owner never keys or plays a request of another mode
             (WstxTransmit::StationModeGate), so no transmission of the old mode starts
             on the new mode's dial in the interval before the step; the contact's
             disarm cause is then refused (staleRequest) instead of contactCancelled. */
    }
    action def SelectDecodedRow {
        in rowIdentity : String;
        out prepared : Contact[0..1];
        doc /* CL-010-01. rowIdentity is the full validated profile/boot/source/job/
             generation/sequence tuple of a live result row with a concrete 'from' call:
             a standard i3=1/2 message (WstxOfflineDecode::StandardFields) whose 'from'
             is a concrete call or a hash the station filled in (HashResolution), or a
             nonstandard i3=4 message (#24 S1b), whose 'from' and 'to' are the full call
             and the filled-in hash in their hash_second order, a CQ having 'to' CQ and
             an RRR/RR73/73 its roger exchange (none: blank). A 'to' hash filled in with
             my call is my call. Effects, after server
             acknowledgement only (DMR handleDecodeSelection ~320-360, D-adopted):
             dxCall = the row's 'from' call; dxGrid = the row's grid exchange if any
             (a row without a grid of the same partner and mode keeps the known dxGrid,
             as WSJT-X's DX Grid, #11; EnterDxStation sets exactly the grid entered);
             report from the row SNR, with the exception stated there (ReportRange); rxOffsetHz = row frequency rounded
             to integer Hz; txOffsetHz = the same, unless Hold Tx is on (the default, CL-039-08) or the row's
             'to' call is my call (replying to me keeps my Tx frequency, DMR ~320-333);
             txParity = opposite of the row's period parity; message set generated, except the texts kept for the same active partner (ContactSnapshot dialogue);
             nextSlot and state per FirstSlotOnSelection. Unresolved hashes (<...>), rows
             without a concrete call, a DX call that would pair two nonstandard calls,
             old/wrong-profile tuples and other families are refused with a reason (an
             EU VHF row is selectable while eu_vhf is set, EuVhfExchange, #99).
             Received partner messages count by the same row reading, so a compound QSO
             sequences as a standard one (AutoSequence). Never sets enableTx (DIFFERENT from
             CFG quick_call "double-click sets Tx enable": #10 safety rule; the browser's
             double-click sends SetEnableTx on after it, OperatingLayout BandActivity) and
             never clears it: a replacement while Enable Tx is on keeps it on
             (ChangeContact). */
    }
    calc def FirstSlotOnSelection {
        in toIsMyCall : Boolean;
        in exchangeKind : String;
        in tx1Skipped : Boolean;
        return slot : TxSlot;
        doc /* DMR ~528-704. Row not addressed to me (CQ, or to another station): tx1
             (state replying), or tx2 (state report) when Tx1 is skipped. Row
             addressed to me: grid -> tx2/report; report -> tx3/rogerReport;
             R+report -> tx4/rogers; RRR or RR73 -> tx5/signoff; 73 -> tx5/signoff
             (logged once tx5 is sent, DirectLog). Responding to a station that answered
             my CQ is this case; CQ response mode (automatic choice of the responder)
             was #12 (D6): a reply to my CQ needs this explicit selection unless CallFirst
             answers it (#10, operator 2026-11-02, Call 1st on by default). */
    }
    action def EnterDxStation {
        in dxCallText : String;
        in dxGridText : String[0..1];
        out prepared : Contact[0..1];
        doc /* D1 adopted (MW dxCallEntry/dxGridEntry, on_dxCallEntry_returnPressed): call a
             station that was not decoded. The call is upper-cased; it must give a
             StandardMessageSet (a standard call, optionally /R or /P, or a nonstandard
             call with my standard call, #24 S1b), else refused invalid_call (no message
             set, no contact). Grid is
             optional, 4 or 6 Maidenhead characters (AA00..RR99[AA..XX]) else refused.
             Enter or Generate creates the contact with origin manualEntry, state
             replying, nextSlot tx1 (tx2/report when Tx1 skipped), the current report
             value, unchanged Rx/Tx offsets and the current Tx-period choice. Never
             sets enableTx. Same ChangeContact rule as selection while a contact is
             active. */
    }
    action def ChangeContact {
        doc /* Explicit server-accepted replacement of an active partner: the old
             contact is cancelled before the new one is prepared; Enable Tx keeps its
             state (#50, operator 2026-11-02, as WSJT-X 3.3.0-beta5: handleDecodeSelection,
             widgets/mainwindow.cpp ~9122-9229, replaces the DX call and regenerates the
             messages through processMessage and never turns Enable Tx off, except an
             Alt double-click; DecodedMessageReaction.cpp appendReactedTail ~365-413 sets
             DX call/grid, report and messages and, with quick_call "Double-click on call
             sets Tx enable", Enable Tx on), so while it is on the next period of the new
             contact's parity carries the new contact's next message (the pending request
             of the old contact is replaced; a transmission already on the air continues,
             as with CancelContact; a replacement in my own period after PTT is keyed and
             before its audio starts replaces that period's request, so the new message is
             sent in it; when the new contact has the other parity, the keyed message is
             sent and the new one is queued for the next period of its parity, never
             refused busy, #10). The replacement itself never turns Enable Tx on. During a station
             automation run without a strategy (WstxMcp OperatingAutomation; a strategy run:
             WstxStrategy::ManualIntervention, #39) an operator replacement of the
             run's contact ends the run, which disarms (contact_changed, TC-020-003); this
             exception stands until the operator decides otherwise. A
             completed contact is not active and is already logged (DirectLog), so a new
             partner simply replaces it (#41: no held unsaved contact). */
    }
    action def CallFirst {
        doc /* #10 (operator 2026-11-02). WSJT-X 3.3.0-beta5 calls Call 1st the respond
             policy "CQ: First" (widgets/mainwindow.cpp ~1489-1493 respondComboBox;
             updateRespondTarget ~17697-17731: the first current-period caller,
             claimFirst per decode period, processed as a double-click with
             auto_tx_mode(true); AutoRespondPeriod.cpp ~11-32
             isDirectAutoRespondCandidate: addressed to my call, a callsign sender other
             than me, an exchange that is not R+report, RRR, RR73 or 73): while the
             contact is calling (an own CQ started by the operator; an MCP run keeps its own rules, WstxMcp; a CQ called by automation: the automation answers its callers only with Calling stations are answered on, WstxStrategy::CallerOfMyCall, WstxContest::ContestRun) with Enable Tx,
             Auto Seq and Call 1st on (WSJT-X AutoRespondPeriod.cpp observePeriod opens
             the respond period only while Enable Tx is on), the first decoded row of the step, in decode order (row
             sequence), that is a standard message to my call from a concrete call in the
             station's mode (neither call a filled-in hash nor an i3=4 message: WSJT-X's
             recipient and sender words must be plain calls), decoded in a period of the parity opposite to my Tx parity,
             whose exchange is a grid or a report, is answered at once as SelectDecodedRow
             of that row (prepareReply: report Tx2 after their grid, roger report Tx3
             after their report, as FirstSlotOnSelection; Hold Tx and the to-my-call rule
             keep my Tx offset). Enable Tx keeps its state, so the next own period answers
             that caller; the answer is automatic, not operator activity. At most one caller is answered: the contact is then no longer
             calling. With Call 1st off a calling contact moves only on an operator
             selection (#12). */
    }
    action def CancelContact {
        doc /* Abort the current contact: disarm (Enable Tx off), clear DX call/grid and
             Tx1-Tx5, select Tx6 (MW abortQSO ~9637). A transmission in progress
             continues unless Halt is also requested. A completed contact keeps its
             fields (only Tx6 is selected), so Log QSO can still re-log it (DirectLog). */
    }

    // ---------------------------------------------------------------- sequencing
    enum def ReceivedKind {
        enum grid; enum signalReport; enum rogerReport; enum rogers; enum seventyThree;
        enum otherFromPartner; enum partnerToOtherStation;
    }
    enum def SequenceEvent {
        enum prepareReply; enum startCq; enum receivedFromPartner; enum transmittedSignoff;
        enum cancel; enum halt; enum watchdogExpired; enum partnerWorksOther; enum none;
    }
    state def AutoSequence {
        attribute acceptedEvent : SequenceEvent;
        attribute received : ReceivedKind;
        attribute addressedToMe : Boolean;
        attribute fromPartner : Boolean;
        attribute autoSequenceOn : Boolean;
        attribute tx4IsRr73 : Boolean;
        attribute sentTx4 : Boolean;
        attribute firstSlot : TxSlot;
        attribute startedWithTx1Skipped : Boolean;
        entry; then idle;
        state idle; state calling; state replying; state report; state rogerReport;
        state rogers; state signoff; state completed; state cancelled;
        transition cq first idle if acceptedEvent == SequenceEvent::startCq then calling;
        transition prepareIdleTx1 first idle if acceptedEvent == SequenceEvent::prepareReply and firstSlot == TxSlot::tx1 then replying;
        transition prepareIdleTx2 first idle if acceptedEvent == SequenceEvent::prepareReply and firstSlot == TxSlot::tx2 then report;
        transition prepareIdleTx3 first idle if acceptedEvent == SequenceEvent::prepareReply and firstSlot == TxSlot::tx3 then rogerReport;
        transition prepareIdleTx4 first idle if acceptedEvent == SequenceEvent::prepareReply and firstSlot == TxSlot::tx4 then rogers;
        transition prepareIdleTx5 first idle if acceptedEvent == SequenceEvent::prepareReply and firstSlot == TxSlot::tx5 then signoff;
        transition prepareCqTx1 first calling if acceptedEvent == SequenceEvent::prepareReply and firstSlot == TxSlot::tx1 then replying;
        transition prepareCqTx2 first calling if acceptedEvent == SequenceEvent::prepareReply and firstSlot == TxSlot::tx2 then report;
        transition prepareCqTx3 first calling if acceptedEvent == SequenceEvent::prepareReply and firstSlot == TxSlot::tx3 then rogerReport;
        transition prepareCqTx4 first calling if acceptedEvent == SequenceEvent::prepareReply and firstSlot == TxSlot::tx4 then rogers;
        transition prepareCqTx5 first calling if acceptedEvent == SequenceEvent::prepareReply and firstSlot == TxSlot::tx5 then signoff;
        transition gridToReport first replying if acceptedEvent == SequenceEvent::receivedFromPartner and autoSequenceOn and addressedToMe and fromPartner and received == ReceivedKind::grid then report;
        transition reportFromReplying first replying if acceptedEvent == SequenceEvent::receivedFromPartner and autoSequenceOn and addressedToMe and fromPartner and received == ReceivedKind::signalReport then rogerReport;
        transition reportFromReport first report if acceptedEvent == SequenceEvent::receivedFromPartner and autoSequenceOn and addressedToMe and fromPartner and received == ReceivedKind::signalReport then rogerReport;
        transition rogerReportFromReplying first replying if acceptedEvent == SequenceEvent::receivedFromPartner and autoSequenceOn and addressedToMe and fromPartner and received == ReceivedKind::rogerReport then rogers;
        transition rogerReportFromReport first report if acceptedEvent == SequenceEvent::receivedFromPartner and autoSequenceOn and addressedToMe and fromPartner and received == ReceivedKind::rogerReport then rogers;
        transition rogerReportRepeat first rogerReport if acceptedEvent == SequenceEvent::receivedFromPartner and autoSequenceOn and addressedToMe and fromPartner and received == ReceivedKind::rogerReport then rogers;
        transition rogersToSignoff first rogerReport if acceptedEvent == SequenceEvent::receivedFromPartner and autoSequenceOn and addressedToMe and fromPartner and received == ReceivedKind::rogers then signoff;
        transition seventyThreeInRogerReport first rogerReport if acceptedEvent == SequenceEvent::receivedFromPartner and autoSequenceOn and addressedToMe and fromPartner and received == ReceivedKind::seventyThree then signoff;
        transition rogersRepeat first signoff if acceptedEvent == SequenceEvent::receivedFromPartner and autoSequenceOn and addressedToMe and fromPartner and received == ReceivedKind::rogers then signoff;
        transition rogersInRogers first rogers if acceptedEvent == SequenceEvent::receivedFromPartner and autoSequenceOn and addressedToMe and fromPartner and received == ReceivedKind::rogers then signoff;
        transition rogersFromReplying first replying if acceptedEvent == SequenceEvent::receivedFromPartner and autoSequenceOn and addressedToMe and fromPartner and received == ReceivedKind::rogers then signoff;
        transition rogersFromReport first report if acceptedEvent == SequenceEvent::receivedFromPartner and autoSequenceOn and addressedToMe and fromPartner and received == ReceivedKind::rogers then signoff;
        transition reportBackFromRogers first rogers if acceptedEvent == SequenceEvent::receivedFromPartner and autoSequenceOn and addressedToMe and fromPartner and received == ReceivedKind::signalReport then rogerReport;
        transition seventyThreeInRogers first rogers if acceptedEvent == SequenceEvent::receivedFromPartner and autoSequenceOn and addressedToMe and fromPartner and received == ReceivedKind::seventyThree then completed;
        transition sentRr73 first rogers if acceptedEvent == SequenceEvent::transmittedSignoff and sentTx4 and tx4IsRr73 then completed;
        transition sent73 first signoff if acceptedEvent == SequenceEvent::transmittedSignoff then completed;
        transition otherStationWhileReplying first replying if acceptedEvent == SequenceEvent::partnerWorksOther and autoSequenceOn then replying;
        transition otherStationWhileReport first report if acceptedEvent == SequenceEvent::partnerWorksOther and autoSequenceOn and startedWithTx1Skipped then report;
        transition cancelCalling first calling if acceptedEvent == SequenceEvent::cancel or acceptedEvent == SequenceEvent::halt or acceptedEvent == SequenceEvent::watchdogExpired then idle;
        transition cancelReplying first replying if acceptedEvent == SequenceEvent::cancel then cancelled;
        transition cancelReport first report if acceptedEvent == SequenceEvent::cancel then cancelled;
        transition cancelRogerReport first rogerReport if acceptedEvent == SequenceEvent::cancel then cancelled;
        transition cancelRogers first rogers if acceptedEvent == SequenceEvent::cancel then cancelled;
        transition cancelSignoff first signoff if acceptedEvent == SequenceEvent::cancel then cancelled;
        doc /* Transition table (DMR planProcessMessage ~528-655, planAutoSequence ~724;
             MW guiUpdate ~8056-8091). prepareReply is SelectDecodedRow or EnterDxStation;
             firstSlot is the FirstSlotOnSelection result (tx1 replying, tx2 report incl.
             a Tx1-skip start, tx3 rogerReport, tx4 rogers, tx5 signoff). A selection
             while a contact is active first passes ChangeContact (cancel, then
             prepare; Enable Tx unchanged). CallFirst is a prepareReply from calling.
             Next message per state: calling tx6, replying tx1,
             report tx2, rogerReport tx3, rogers tx4, signoff tx5; completed and
             cancelled select tx6 with Enable Tx off.
             Received messages count only when: Auto Seq on, a standard message whose
             'to' is my profile callsign and 'from' the contact's DX call, decoded in the
             partner's period, at any audio frequency (DMR ~724). Messages of other
             stations never change the sequence (DMR ~517-524) but stay visible in the
             Rx Frequency pane. Classification: grid exchange -> grid; report without
             R -> signalReport; R+report -> rogerReport; RRR or RR73 -> rogers; 73 ->
             seventyThree. One decoded row (same validated identity tuple) counts once,
             however often it is delivered or re-read; a re-decode of the same period
             yielding the same partner message also counts once per period.
             Repeats: no retry counter or timeout (WSJT-X has none for FT8, DMR/MW
             ~8844 fast modes only); the next message is sent again each of my periods
             while Enable Tx is on until a counted message changes the state; the Tx
             watchdog (TxWatchdog) bounds unattended repetition. A repeated earlier
             partner message maps back as WSJT-X does: a signalReport in rogers returns
             to rogerReport (resend Tx3); R+report in rogerReport/rogers keeps rogers
             (resend Tx4); rogers in signoff resends Tx5. A 73 in rogerReport (the
             partner skipped RR73 after my R+report) moves to signoff: my 73 is sent once
             and the contact completes on it (#11 supervisor default). A rogers (RRR or
             RR73) moves to signoff in every active state before signoff, as WSJT-X
             (DMR ~585-600: rogerAck selects Tx5; MW ~8237-8249 logs on the first 73
             sent): in rogerReport after my R+report; in rogers after my Tx4 RRR, or after
             a Tx4 RR73 whose transmission did not complete (#69, live stall 2026-11-08:
             the partner's RR73 after my RRR was answered with RRR until a halt); and in
             replying or report, when the partner signs off before I received his report
             or R+report (#69, operator 2026-11-08). In each case my 73 is sent once and
             the contact completes on it and is logged once (sent73, DirectLog); no
             report received leaves RST_RCVD absent. A rogers or 73
             counted while my Tx1-Tx4 is already pending for the next period replaces that
             request with Tx5 until its audio starts; after the audio start the message of
             that period is sent and Tx5 follows in my next period (TransmitSubmission).
             With Auto Seq off a counted partner message changes no state (it still
             updates the received report and TIME_OFF); the step Auto Seq would take is
             offered as ContactSnapshot suggested_slot and the QSO pane shows the Auto
             Seq state and that offer, so a signed-off partner is never silently
             answered with a repeat (#11 live stall 2026-11-02).
             Messages not in the table
             (grid in report.., 73 in replying, report or signoff, anything after
             completed/cancelled) change nothing.
             Completion: transmittedSignoff is TransmitService's confirmed completed
             transmission of a Tx4 RR73 or Tx5 73 of this contact (MW message_is_73
             ~492, m_sentFirst73). On completion Enable Tx turns off (CFG
             disable_TX_on_73 default true ~3746) and the contact is logged once
             (DirectLog, #41). Receiving 73 while in rogers (after Tx4 RRR) completes without
             sending more (DMR ~601-616); receiving RRR or RR73 there sends my 73 first
             (signoff, #69). DIFFERENT: WSJT-X then leaves Enable Tx on
             with Tx6 selected; here Enable Tx turns off because Auto Seq never
             starts another contact (#10).
             partnerWorksOther (DMR planAutoSequence ~775-791, MW ~7427
             auto_sequence(decodedtext,25,50); 50 Hz rule): in replying, or in report
             when the contact started with Tx1 skipped, with Auto Seq on, the DX call's
             decoded message to another call within 50 Hz inclusive of my txOffsetHz
             disarms and stops a transmission already started by an abort
             (WstxTransmit::AbortTransmission, never a halt: #39 2026-11-04, normal flow
             never uses HALT); the state is kept. The stop is recorded with DisarmCause
             partnerWorksOther (CL-111-03). A contact that pauses
             for a busy partner (a manual contact; a run's own contact with busy_pause on;
             TxWatchdog busy pause, BusyPartner) does not disarm here: its Tx moves clear of his
             signal (FT8 100 Hz, FT4 140 Hz between the lower edges) and the call goes on; only a
             refused move disarms as here. A pounce, an MCP policy run and a run with busy_pause off
             keep this stop (50 Hz inclusive).
             halt and watchdogExpired turn Enable Tx off and keep the state (the
             contact can resume after an explicit Enable Tx), except in calling where
             the CQ ends. cancel follows CancelContact. Esc is Abort QSO (AbortQso), not a halt. */
    }
    attribute def TransmitSubmission {
        attribute contactId : String;
        attribute slot : TxSlot;
        doc /* How QsoAndLogging uses WstxTransmit::TransmitRequest. While armed it keeps
             one pending request for the next period of the contact's txParity with the
             current nextSlot text, txOffsetHz and mode, and a new requestSequence for
             every change. A sequence, text, report or offset change replaces the pending
             request through #9 until its audio starts; #9 then refuses audioStarted and
             the change applies to the following period (D7; the #37 fold-out Now of a Tx
             line chooses it next and turns Enable Tx on, so it too goes from the next own
             period, never into a waveform already on the air). lastTransmittedText changes only on a started outcome; the contact
             reaches completed only on a completed Tx4 RR73/Tx5 73 outcome; refused or
             failed outcomes disarm with the visible refusal. A client timeout, colour
             change or disconnected press never means RF stopped. Tx offset domain FT8
             200..2950 Hz (Ft8WaveformContract tone 0; FT4-NOTE 200..2916). */
    }
    action def SetEnableTx {
        in enable : Boolean;
        doc /* #37 (operator design interview 2026-11-01): there is no Enable Tx control.
             Starting a QSO means transmitting: the QSO pane CQ button (no transmitting
             contact: a new own CQ; an active contact is cancelled first after a
             confirmation), a double-click on a decoded row
             (SelectDecodedRow, then on) and RR73/73 (choose Tx4 RR73/Tx5, then on; offered
             only while the contact is in progress, never on a completed or cancelled one,
             where Enable Tx would start a fresh own CQ) send
             enable_tx {enabled:true} with the shown safety revision, so grant, clock,
             period and safety-revision checks are unchanged; the CQ button, an explicit
             operator choice like the double-click, retries their enable_tx at most twice after a
             stale_revision refusal with the reloaded snapshot (CL-061-02). Transmission ends by itself
             on completion (Enable Tx off after a completed Tx4 RR73/Tx5 73, see the
             transition table), by the Tx watchdog, by Cancel contact or F4 (the contact
             is cancelled, a transmission already on the air finishes), by Abort QSO (Esc,
             AbortQso: the transmission stops now) or by HALT, the emergency stop. Alt+N has no
             function. Earlier text: Separate explicit operator action (Alt+N where the browser delivers it,
             HT Alt+N). Maps to WstxTransmit::TransmitArming (armed/disarmed is #9
             state). On: transmissions of the next slot start in the contact's parity
             periods through TransmitSubmission; with no partner, next Tx6 means
             calling CQ (state calling). Off (disarm): no new request; a transmission
             already started finishes (WSJT-X Enable Tx off lets the current Tx finish). */
    }
    attribute def StartActions {
        doc /* CL-111-02, CL-111-05, CL-111-07, CL-111-08. The start actions switch the
             transmit state (WstxTransmit::TransmitArming) on. Each is one ContactCommand
             that carries the CL-022 safety revision shown to its sender: reply (the row's
             SelectDecodedRow with replace true, then on), call_cq (the only start that
             calls CQ), call_dx (EnterDxStation, then on), send_next (chooses the slot of
             the current QSO, then on) and reset_repetitions (a new repetition count of
             the message due next, TxWatchdog). A start by the operator in the browser
             switches on with cause operator; a start by a run or an MCP client is
             automatic, switches on with cause auto and is refused tx_watchdog after a
             repetition-limit stop or when no browser action was seen this boot;
             reset_repetitions from a run or an MCP client is refused operator_required.
             An operator start that finds the state off opens a new repetition count.
             "QSO" is a contact with a partner in replying to signoff. Outcome per state
             before (reply | call_cq | call_dx | send_next | reset_repetitions):
             no contact, idle: prepares the row's QSO, on | a new own CQ, on | prepares,
             on | no_contact | no_contact.
             own CQ calling: the CQ is replaced by the row's QSO, on | state on: accepted,
             nothing changes; state off (kept after a lost radio or a refusal): the same
             CQ, on | the CQ is replaced, on | no_contact | no_contact.
             QSO, state on: another partner: the old QSO is cancelled, the new one
             prepared; the same partner: the QSO continues at the row's message with the
             same contact identity; on | contact_active | replace false: contact_active,
             also for the QSO's own partner; replace true: the old QSO is cancelled and a
             new one prepared (a new contact identity for the same partner too), on |
             chooses the slot, stays on | a new count, stays on.
             QSO kept, off, cause txWatchdog: as the row above, on | contact_active | as
             the row above | chooses the slot, on | a new count, on, the message due next
             is sent.
             QSO kept, off, any other cause: as the row above, on | contact_active | as
             the row above | chooses the slot, on | state_conflict.
             completed, cancelled: prepares the row's QSO, on | a new own CQ, on |
             prepares, on | no_contact | no_contact.
             A Hound's call_cq is no_contact. A slot without text is invalid_message, as
             choose_next. A safety revision other than the station's is stale_revision
             with field safety_revision. A start that arrives after a stop of the same
             station step is refused state_conflict (WstxTransmit::StopOrder). A refused
             start changes nothing: no QSO is prepared.
             When reply or call_dx is admitted but transmission is not possible (no
             transmit capability: transmit_unsupported; radio, its PTT switch or
             authorization not ready by the transmit owner's arm conditions
             (WstxTransmit::TransmitArming): radio_unavailable or not_authorized; clock
             not synchronized: clock_not_synchronized; Tune on: busy), the command is accepted, the QSO is
             prepared, the transmit state stays off with its causes unchanged and the
             transmit view's refusal is that reason; nothing starts by itself when the
             reason goes away. call_cq, send_next and reset_repetitions in the same
             situation are refused with that reason as their ContactRefusal
             (transmit_unavailable, clock_not_synchronized or busy) and change nothing.
             select_row, enter_dx and choose_next never start. */
    }
    dependency startActionsClause from StartActions to WstxRequirements::'CL-111-02';
    dependency startNeverCqClause from StartActions to WstxRequirements::'CL-111-05';
    dependency startCannotTransmitClause from StartActions to WstxRequirements::'CL-111-07';
    dependency resetClause from StartActions to WstxRequirements::'CL-111-08';
    action def BandChange {
        doc /* CL-111-03. A contact holds the station band it was prepared on. The station
             band is the radio's dial band, else the band of the operating selection
             (WstxStrategy station band). When it differs from the contact's band, the
             engine at its next step or command switches the transmit state off
             (DisarmCause bandChanged; a transmission on the air finishes) and cancels a
             contact in calling, replying, report, rogerReport, rogers or signoff as
             ModeChange does (calling -> idle; a QSO -> cancelled, DX call and Tx1-Tx5
             cleared, Tx6 next). A completed, cancelled or idle contact keeps its fields
             and takes the band. An unknown station band is no band change, and a
             contact prepared while the band was unknown takes the first band seen. */
    }
    dependency bandChangeClause from BandChange to WstxTransmit::'CL-111-03';
    action def HaltTx {
        doc /* The operator's emergency stop (operator decision #39, 2026-11-04: HALT is
             emergency only and only manual): the Halt Tx buttons and Alt+H (HT). Sends
             WstxTransmit::HaltTransmit (POST /transmit/halt), stopping a transmission
             or Tune now and disarming (MW on_stopTxButton_clicked). Esc is no longer a
             halt (AbortQso). Shown as halted only after #9 confirms; until then
             pending/unknown. The keyboard halt is sent by the always-loaded page script
             (never waiting for the contact client), skipped only when the station is
             known receive-only. The remote emergency stop is MCP wstx_transmit_halt only;
             UDP has no Halt Tx. The station and its automation never send it in normal flow
             (WstxTransmit::TransmitHaltUse). */
    }
    action def AbortQso {
        doc /* Abort QSO (operator decision #39, 2026-11-04, "stop the transmission and
             the QSO immediately, but not HALT the system"): Esc and the "Abort QSO"
             button beside HALT send ContactCommand abort {}. The station stops the
             current transmission or Tune now (WstxTransmit::AbortTransmission: audio
             stopped, PTT released with readback, requests dropped, Enable Tx off with
             cause contactCancelled) and cancels the contact as CancelContact (nothing
             logged; a completed contact only selects Tx6 and keeps its fields). It is no
             halt: halt_state and the halt count are unchanged and the station stays
             ready for the next QSO. Like cancel it is accepted on any older contact
             revision. Esc (MW keyPressEvent ~3683 abortQSO) acts on every page state and
             in every focused field and closes no panel; an open dialog or menu takes Esc
             first. With nothing active (no contact in progress, disarmed, not
             transmitting) the button is disabled and Esc sends nothing. A running station
             automation run reacts to the cancelled contact as to any operator contact
             change. */
    }

    // ---------------------------------------------------------------- watchdogs
    attribute def TxWatchdog {
        attribute limitCalls : Integer = 6;
        attribute minimumCalls : Integer = 1;
        attribute maximumCalls : Integer = 99;
        attribute remainingCalls : Integer;
        assert constraint limitDomain { limitCalls >= minimumCalls and limitCalls <= maximumCalls }
        doc /* Operator rule #39, 2026-11-06 (replaces the WSJT-X time watchdog, CFG
             TxWatchdog ~3749, MW tx_watchdog ~14646, and the unanswered count of
             2026-11-04): the Tx watchdog limits how often one message is repeated, in
             manual operation and under automation alike, whatever the message (CQ,
             Tx1..Tx5, free text), except a strategy run's own contact while the run is attended,
             which has no stop (WstxStrategy::StrategyWatchdog; WD:n shows only this watchdog,
             never the run's leave count). Server-owned station-session setting: limit 1..99
             repetitions, default 6 at each station start. DIFFERENT: WSJT-X 0 = disabled
             is not offered; a safety bound always applies.
             It keeps no count of its own: the repetition count is the Rep of the
             ContactSnapshot dialogue, the count of the newest tx entry when that entry
             holds the message due next, otherwise 0. Whatever restarts that Rep is the
             only restart: a different message (the exchange advanced), a new contact, and
             one addition for the operator: an operator Enable Tx while Enable Tx
             is off makes the next transmission open a new tx entry, so a stopped station
             may send the same message again; while it is on it restarts nothing. Partner messages, browser clicks, settings, Auto Seq, MCP
             and automation requests restart nothing by themselves.
             Stop: when the send due next would exceed the limit it is never planned or
             keyed: 1.2 s into its period (past the latest live decode measured, #47) Enable
             Tx goes off (cause txWatchdog), PTT stays released, nothing is halted (no HaltTransmit,
             halt_state unchanged), a transmission already keyed finishes, the contact
             state is kept and the station shows "Tx watchdog: same message sent N times" until
             the next Enable Tx. A partner message decoded before that moment still changes
             the message due next, sent by a late start as below the limit. A request still pending when
             the send due next is at the limit (the limit lowered, or a Tx button going back to
             a message at its limit) would key, so Enable Tx goes off at once. The repetitions left are shown while Enable Tx is on
             (WD:n, watchdog tx_remaining_calls = limit - Rep, less the paused calls below).
             Automation (WstxStrategy::WatchdogFromOperator): an automatic Enable Tx is
             refused tx_watchdog after a stop or while no browser action was seen this
             boot; only the browser may set the watchdogs (set_watchdogs from another
             source is refused operator_required). A new message or target chosen by a run
             restarts the Rep like any other, so a run is bounded per message, not in
             total. Mouse movement the server cannot observe is not activity.
             Busy pause (#97 decision 7, BusyPartner; operator #93 2026-11-09 "Keep calling, don't
             count"): a send of the message due next while the partner is busy at its stop point
             (1.2 s into its period, BusyPartner) is a paused call and does not count toward the
             limit: the counted repetitions are Rep minus the
             paused calls of that tx entry, and tx_remaining_calls = limit - counted. The paused
             calls of one message are at most limitCalls (operator 2026-11-09, #97 Q5: at most N
             paused calls per message, N the limit); a further send while he is busy counts. So
             one message is sent at most twice the limit; nothing the partner does can extend it.
             A new message or contact restarts the paused count with the Rep; the operator's Enable
             Tx while off restarts it as it restarts the Rep. Which contacts pause: a manual contact
             (operator 2026-11-09, #97 Q7 "yes, both") and a strategy or contest run's own contact
             whose strategy has busy_pause on (WstxStrategy::BusyPause; the run's own contact has no
             stop while attended, StrategyWatchdog, so there the pause counts for the leave rule).
             A pounce and an MCP policy run never pause. */
    }
    attribute def BusyPartner {
        attribute busyPausedCallsMax : Integer = 6;
        doc /* #97 decision 7 (operator #93 2026-11-09; it replaces the WSJT-X stop of
             partnerWorksOther for the contacts that pause, AutoSequence; the #93 draft fca9822fe
             compared). Starts: a decoded standard message from the partner (the contact's DX
             call) to another call than mine that carries a grid, a report or an R-report (his QSO
             with that station in progress, also his own Tx1 to it); a hashed call "<...>" that is
             not filled with my call (WstxContact's hash table does not resolve it to my call) is
             another call. Holds (operator #93: "we pause counting ... till the called station
             finishes its other qso"): from then on, however long he is not decoded and also when
             he goes on with a further station, until he ends it: his RR73, RRR or 73 to another
             call, his CQ, his free text (a free text has no sender: it counts as his when decoded in
             his period within 10 Hz of his last decode; #97 coordinator default), or any message from him to my call (progress,
             AutoSequence); a new contact or the end of the contact clears it. Nothing but his own
             messages ends it, and the bound of TxWatchdog (N paused calls per message, #97 Q5)
             keeps it from extending a call without limit.
             When it counts: a send is paused when he is busy at its stop point, 1.2 s into its
             period (TxWatchdog): a publication that ends or starts it arriving before the stop
             point (1.1 s) counts for that send, one arriving after it (1.3 s) for the next.
             Split frequency ("check if we are not on his transmit frequency"; it applies to every
             contact that pauses, also while it is not pausing: an unattended run with busy_pause
             on, or a message whose N paused calls are used up): when he sends a decoded message to
             another call (any, busy or not; the trigger of partnerWorksOther, in replying and in a
             Tx1-skipped report) and my Tx signal is not clear of his signal, Tx moves before my next
             own period to the nearest candidate clear of it. Clear: my signal [f, f + width) keeps
             50 Hz from his [d, d + width): |f - d| at least width + 50, FT8 100 Hz, FT4 140 Hz
             (FT8 99 moves, 100 stays; FT4 139 moves, 140 stays). Candidates: WstxStrategy::FreeTxSlot's
             grid from 500 Hz inside the Tx range, clear of his signal and of decoded stations while
             one is free, at least 50 Hz from a frequency his PSK Reporter spots show him decoding in
             my Tx parity while one is free (else that is not used), the nearest to the current Tx,
             the lower on a tie; Rx stays on him. His decode arriving before the audio start of my
             next send moves the pending request (WstxContact::TransmitSubmission replaces it); one
             arriving after the audio start lets that send finish where it is and moves the next. A
             refused move (set_frequency refused) falls back to the stop of partnerWorksOther (the
             transmit state off, cause partnerWorksOther), so Tx never stays on his signal. In
             manual operation this is the one automatic Tx move besides Hold Tx's rules, also with Hold Tx on (operator
             2026-11-09, #97 Q7 "yes, both"; an exception to CL-039-08); an explicit Tx action of the
             operator (also a click onto his signal) wins until his next message to another call,
             which moves it again. A contact that does not pause (a pounce, an MCP policy run, a run
             with busy_pause off) keeps partnerWorksOther's stop.
             Shown: the contact snapshot's watchdog carries busy_with (null, or the other call as
             decoded, at most 13 characters, "<...>" for an unresolved hash) and paused_calls (the
             paused calls of the message due next); GET /contact stays within its 4096 bytes in the
             maximum shape with a 13-character busy_with. The browser appends " · <call> busy with
             <other>, not counted (<k>/<N>)" to WD:n in the QSO pane and the station bar while
             busy_with is set (in a run's own contact the leave label carries it,
             WstxStrategy::LeaveCountLabel). busyPausedCallsMax is the default limit; the bound is
             the operator's current limitCalls. */
    }
    attribute def TuneWatchdog {
        attribute limitSeconds : Integer = 90;
        attribute minimumSeconds : Integer = 1;
        attribute maximumSeconds : Integer = 300;
        assert constraint limitDomain { limitSeconds >= minimumSeconds and limitSeconds <= maximumSeconds }
        doc /* D4 adopted (CFG TuneWatchdog default true, TuneWatchdogTime default 90 s
             ~3750-3751; mainwindow_slots.cpp ~590; MW stopTuneATU ~12728). Always
             enabled (DIFFERENT: not switchable off), 1..300 s, default 90 s per
             station session. Starts when #9 confirms Tune on; at expiry the server
             ends Tune through #9; the remaining seconds are shown on the Tune control. */
    }

    // ---------------------------------------------------------------- frequencies
    enum def PointerAction {
        enum click; enum shiftClick; enum rightClick; enum ctrlClick;
        enum leftDoubleClick; enum rightDoubleClick;
    }
    calc def PointerEffect {
        in pointerAction : PointerAction;
        in pointerHz : Integer;
        doc /* D3 adopted (PL mouseReleaseEvent ~976, mouseDoubleClickEvent ~1012; MW
             setFreq4 ~12816). pointerAction and pointerHz: pointerHz is the waterfall/spectrum frequency under the
             pointer from the fixed 0..3000 Hz axis, rounded to integer Hz, by the waterfall's one
             frequency mapping (WstxOperatingLayout::RxTxStrip, CL-050-07) (the native/
             projected readout of WstxRecordingReceive is unchanged). #50 (CL-050-01, operator
             2026-11-02, replacing the #37 mapping): click -> Tx, sent after 250 ms so that a
             leftDoubleClick -> Rx and Tx sends only its one request; shiftClick and ctrlClick
             act as click; rightClick and rightDoubleClick set nothing (no context menu).
             No decode-at-point: the fixed full-band decoder always runs and the browser sends
             no redecode. Dragging the Rx or Tx marker sets that offset on release
             (WstxOperatingLayout::RxTxStrip). Explicit Tx pointer actions move Tx even with Hold Tx on, as
             WSJT-X setFreq4 (Hold Tx only stops implicit moves on selection).
             A Tx outside its domain is refused with the domain; Rx accepts 0..3000.
             Each is a server request; markers move only after confirmation, the
             pointer readout is local. Touch: tap = click; Tx/both use the labelled
             numeric inputs. No pointer action enables Tx. */
    }
    attribute def FrequencyControls {
        attribute rxOffsetHz : Integer;
        attribute txOffsetHz : Integer;
        attribute holdTx : Boolean;
        assert constraint rxDomain { rxOffsetHz >= 0 and rxOffsetHz <= 3000 }
        assert constraint txDomain { txOffsetHz >= 200 and txOffsetHz <= 2950 }
        doc /* Labelled numeric Rx Hz and Tx Hz inputs (MW RxFreqSpinBox/TxFreqSpinBox),
             Hold Tx (requested vs confirmed shown separately; on by default, CL-039-08). Tx<-Rx/Rx<-Tx copy
             buttons are not adopted (agent choice 2026-10-31: ctrl-click and the
             numeric inputs cover them); F11/F12 steps are not adopted (D7). FT4-NOTE Tx max 2916. */
    }

    // ---------------------------------------------------------------- Rx pane
    calc def RoutesToRxFrequencyPane {
        in rowFrequencyHz : Real;
        in rxOffsetHz : Integer;
        in firstCallIsMyCall : Boolean;
        in containsMyCallAndDxCall : Boolean;
        return routed : Boolean = firstCallIsMyCall or containsMyCallAndDxCall or
            (rowFrequencyHz >= rxOffsetHz - 10.0 and rowFrequencyHz <= rxOffsetHz + 10.0);
        doc /* #37 (2026-11-02): no browser pane shows the routed rows any more; the
             compact QSO pane (WstxOperatingLayout::QsoPane) shows the last partner message
             and at most two other stations instead. The completion and log rules below
             are unchanged. Earlier text:
             D2 adopted (DOP decideRouting ~391-441): a decoded row is shown in the Rx
             Frequency pane when its audio frequency is within +/-10 Hz inclusive of the
             confirmed Rx offset (FT8 and FT4 alike), or its first ('to') call equals
             the profile callsign exactly, or it contains my call followed by the DX
             call. It also stays in Band Activity. The station's own transmitted
             messages appear in the pane labelled Tx with their period UTC (CFG
             Tx2QSO default true; MW displayTransmittedText ~8151). The pane
             accumulates rows across periods in the browser from results it already
             receives (no extra request), newest last, at most 500 rows (own bound),
             with the same unread/resume-follow behaviour as Band Activity; it clears
             on profile change, mode/band change and Erase (local only). An Rx change
             affects only later routing. Selecting a pane row is SelectDecodedRow. */
    }

    // ---------------------------------------------------------------- log
    attribute def LogRecord {
        attribute contactId : String;
        attribute call : String;
        attribute gridsquare : String[0..1];
        attribute mode : String;
        attribute submode : String[0..1];
        attribute rstSent : String[0..1];
        attribute rstRcvd : String[0..1];
        attribute qsoDate : String;
        attribute timeOn : String;
        attribute qsoDateOff : String;
        attribute timeOff : String;
        attribute band : String[0..1];
        attribute freqMHz : String[0..1];
        attribute stationCallsign : String;
        attribute myGridsquare : String[0..1];
        attribute txPwrW : String[0..1];
        attribute commentText : String[0..1];
        attribute contestFields : String[0..8];
        attribute confirmationFields : String[0..7];
        attribute activity : String[0..1];
        doc /* ADIF 3.1.8 ADI fields (field set follows ADQ to_adif ~50-75 and LQ, D10):
             CALL, GRIDSQUARE (only when known; DIFFERENT from WSJT-X writing it empty),
             MODE FT8 (FT4-NOTE MODE MFSK, SUBMODE FT4), RST_SENT = report of the last
             transmitted Tx2/Tx3 (MW ~8105-8127), RST_RCVD = the partner's last counted
             report, both rendered as in ReportRange; QSO_DATE/QSO_DATE_OFF YYYYMMDD,
             TIME_ON/TIME_OFF HHMMSS UTC; BAND from the confirmed dial frequency per the
             ADIF band enumeration (e.g. 20m), absent when the dial is not confirmed;
             FREQ in MHz with six decimals = confirmed dial + Tx offset (LQ ~384,
             mainwindow_slots.cpp ~545), absent when unconfirmed; STATION_CALLSIGN and
             MY_GRIDSQUARE the profile locator; TX_PWR watts (decimal >0, optional, D10); COMMENT single
             line, printable ASCII without '<' and '>', at most 1024 characters
             (optional, D10); a COMMENT containing '<' or '>' is refused (DIFFERENT from
             WSJT-X to_adi_text stripping them: a supplied record is never altered).
             DirectLog writes neither TX_PWR nor COMMENT (no power or comment entry
             since #41 retired the review); SaveContact and UpdateLogbook may carry them.
             Contest fields (#24 S2b, ContestExchange; D10 reversed for these only), in
             this order after COMMENT: STX, STX_STRING, SRX, CONTEST_ID, SRX_STRING, CLASS,
             ARRL_SECT, STATE; each at most 32 printable ASCII characters without '<' and
             '>' (STX/SRX 1-4 digits). Confirmation fields (#10, operator 2026-11-04, for
             the strategies of class strategy), in this order after the contest fields:
             LOTW_QSL_RCVD, LOTW_QSLRDATE, QSL_RCVD, QSLRDATE, QSL_RCVD_VIA, EQSL_QSL_RCVD,
             EQSL_QSLRDATE; the statuses the ADIF 3.1 QSL Rcvd enumeration Y, N, R, I, V,
             the dates YYYYMMDD, QSL_RCVD_VIA the QSL Via enumeration B, D, E, M (values
             case-insensitive, stored as written). A record is confirmed when any of the
             three statuses is Y or V; N, R, I and absent are not confirmed. Only
             UpdateLogbook sets them; DirectLog and SaveContact never write them, a DirectLog
             replacement keeps the stored ones, and the one-record-per-contactId
             comparison ignores them. In the stored log a confirmation field that is invalid
             or repeated (a log kept verbatim before #10) stays an unknown field. RST_SENT/RST_RCVD are a ReportRange report, a
             5n9 RST (n 2-9) or a 5n RS 52..59 (EuVhfExchange, #99, operator 2026-11-09). APP_WSTXRUST_CONTACT_ID = contactId; APP_WSTXRUST_SOURCE (a
             token of 1..32 letters, digits or '-') marks a record added by UpdateLogbook
             with the program it came from and is absent on the station's own records.
             APP_WSTXRUST_ACTIVITY (activity) is the contact's activity at logging time,
             one of field_day, rtty, eu_vhf, na_vhf, ww_digi, arrl_digi, hound, absent for
             none (WstxRequirements::'CL-112-05'). App fields follow the fields above in this
             order: APP_WSTXRUST_CONTACT_ID, APP_WSTXRUST_SOURCE, APP_WSTXRUST_ACTIVITY, then
             the preserved unknown fields; they are read back on load and are outside the
             one-record-per-contactId comparison.
             Name, operator, propagation and satellite fields are not adopted (D10; WSJT-X
             writes OPERATOR
             only with a configured operator call, which this product does not have).
             Start time (MW set_dateTimeQSO ~8944): the UTC start of the period of this
             contact's first transmitted Tx2, or one period before its first
             transmitted Tx3; otherwise the start of its first transmitted message's
             period. End time: the UTC end of the last period in which a counted
             message of the contact was transmitted or received. Both server-owned;
             the browser never substitutes its clock. */
    }
    enum def LogOutcome { enum saved; enum alreadySaved; enum invalidField; enum conflict; enum storageFailed; }
    action def DirectLog {
        doc /* #41 (operator design interview on #37, 2026-11-01: no log review queue;
             each completed QSO goes straight to the internal ADIF log, as WSJT-X, and
             to the external programs). Retires the #10 OfferLogReview queue, its
             discard_review action and the browser review form.
             Automatic: once per contactId when it completes (AutoSequence completed:
             after a confirmed transmitted Tx4 RR73 or Tx5 73, or a received 73 in
             rogers), which is when WSJT-X prompts to log (MW guiUpdate ~8056). A
             contact completed without a received report (a selected RR73/73 row, or the
             partner's RRR/RR73 answered in replying or report, #69) is logged the same
             way with RST_RCVD absent. The server builds the LogRecord at completion: CALL,
             GRIDSQUARE when known, MODE/SUBMODE by ContactMode, RST_SENT/RST_RCVD,
             QSO_DATE/TIME_ON and QSO_DATE_OFF/TIME_OFF by the LogRecord time rules, BAND
             and FREQ from the dial confirmed at completion plus the Tx offset (absent when
             unconfirmed), STATION_CALLSIGN and MY_GRIDSQUARE; it is stored without any
             browser, whether or not one is connected. Manual Log QSO (button, Alt+Q,
             open_log): the station accepts it whenever a contact has a DX call, in any
             state; the QSO pane offers the button and Alt+Q only while a QSO runs
             (WstxOperatingLayout::QsoPane, #37); it logs
             that contact now the same way with the times observed so far, without a
             form. Log QSO of an unfinished contact (replying..signoff) also closes it
             (#37, 2026-11-02): it becomes completed with Tx6 selected, Enable Tx turns off
             (disarm cause contactCompleted), nothing stays queued, and it counts as logged
             at completion, so later partner messages neither advance nor log it again.
             One record per contactId: logging a contactId already stored with
             identical fields adds nothing (alreadySaved); with different fields the
             contact's record is replaced in place (replaced), keeping its index. Log QSO of a contact already logged at
             its completion (stored or pending) changes nothing: the record keeps the
             dial, Tx offset and location of completion. A second contact with the same
             station is a new contactId and a new record (WSJT-X LogBook::add appends
             without a dupe check). Only the first store of a contactId (saved) is sent
             to the WstxUdp targets as QSO Logged then Logged ADIF, so each contact
             reaches the external programs once; a replacement stays internal. They are
             sent by the station step, never from inside a command. Idempotence: a retried command_id has no second
             effect, a repeated completion logs once, and a restart starts no contact,
             so it logs nothing again; stored records survive in contacts.adi.
             Storage failure: the record stays pending in the station process, at most 64
             (a 65th drops the oldest pending record with error log_queue_full), retried
             at most every 5 s; pending records do not survive a restart. A record that
             fails the LogRecord domains (for example no profile callsign) is not stored
             (error log_invalid_field). ContactSnapshot log shows the latest attempt.
             Publication runs under the station's authorization lock without a request
             grant: it follows a contact that granted operating requests drove.
             Logged records are not edited here (ContactHistory stays read-only). */
    }
    action def SaveContact {
        in supplied : LogRecord;
        out outcome : LogOutcome;
        doc /* Exactly once per contactId per profile. Storage: the selected profile
             directory's file contacts.adi (ADIF 3.1.8 ADI with header), written as a
             complete new file in the same directory, flushed and atomically replaced,
             as WstxProfiles::SaveSelectedProfile; saved is acknowledged only after the
             replace succeeds. A repeated save of the same contactId with identical
             fields returns alreadySaved and adds nothing; different fields after a
             save return conflict (history is read-only). Failure leaves the request
             visibly unsaved with retry under the same contactId. A new contact with a
             call already in the log is a separate contact (no dupe refusal; WSJT-X
             LogBook::add appends without a dupe check). Since #41 no browser control
             sends it: completed contacts are stored by DirectLog; POST /contacts stays
             the explicit save of a supplied record. */
    }

    // ---------------------------------------------------------------- worked before
    enum def WorkedStatus { enum notWorked; enum workedOtherBandOrMode; enum workedThisBandAndMode; enum unknown; }
    action def WorkedBeforeQuery {
        in call : String;
        in band : String;
        in mode : String;
        out status : WorkedStatus;
        doc /* D9 adopted (WB indexes calls keyed by band+mode and band; LogBook::match).
             Determined by the server from the profile's contacts.adi including contacts
             saved this session and records added by UpdateLogbook (#10, 2026-11-03),
             through an index of the log by call and by grid square that is rebuilt only
             when the log changes, so a record costs a lookup of its call, not a scan
             of the log: workedThisBandAndMode when a record has the same CALL,
             BAND and MODE/SUBMODE; workedOtherBandOrMode when only CALL matches; else
             notWorked. Calls compare case-insensitively on the full call. DXCC entity,
             continent and zone status come with each decoded record instead
             (DecodedEntity, #55); LoTW highlighting is not adopted (B-list of #25). The
             station determines it on each decoded record it serves (worked_status,
             DecodedEntity) and the browser sends no query (#10
             WstxStationProtocol::PushedStationState); a row without the key shows unknown
             (no indicator): a hashed or absent call, or no band known. Indication uses a
             text/icon label plus colour; it changes no decoding, sequence or log.
             Award standing (#10, operator 2026-11-04, consumed by the #39 award
             strategies): the worked set of DecodedEntity holds, for each DXCC entity
             (and continent, CQ and ITU zone) ever, per band and per band and mode, whether
             it is worked and whether a confirmed record (LogRecord confirmationFields)
             holds it, from the same lookup; an entity is needed in a scope when it is not
             worked or not confirmed there. It is rebuilt with the worked set when the log
             changes, including a confirmation upgrade. */
    }

    // ---------------------------------------------------------------- country data (#55)
    attribute def CountryFile {
        attribute bytesMax : Integer = 1048576;
        doc /* #55 (CL-055-01, CL-055-03). The DXCC country table is Jim Reisert AD1C's
             cty.dat as WSJT-X ships it: server/third-party/cty/cty.dat, copied unchanged
             from WSJT-X 3.3.0-beta5 (version VER20250115, 346 entities; source, SHA-256
             and the MIT-style permission notice in NOTICE.md and LICENSE beside it).
             It is embedded in the station. An uploaded file replaces it per station
             profile as cty.dat beside contacts.adi (written to a temporary file, flushed,
             renamed under the publication gate); a stored upload that cannot be read or
             parsed leaves the bundled table in use, is reported and is never
             overwritten. Nothing is downloaded automatically.
             Format (AD1CCty load_cty): an entity line "name: cq: itu: continent: lat:
             lon: utc: primary prefix:" (lon positive West; a leading * marks a WAE-only
             entity) followed by comma-separated entries up to ";"; "=" marks an exact
             call; an entry may carry (cq) [itu] <lat/lon> {continent} ~utc~ overrides.
             Lines that are no entity line are skipped; an invalid number, a CQ zone
             above 40 or ITU zone above 90 (also as an override), an unknown continent, a
             shown name (EntityOfCall) that is not 1..40 printable ASCII characters, a
             missing ";" or a file without entities is refused with the 1-based line, so
             every accepted file gives values the browser accepts. A key listed twice keeps its first entry. "=VERyyyymmdd" is
             the version. */
    }
    calc def EntityOfCall {
        in call : String;
        return entity : String[0..1];
        doc /* #55 (CL-055-01) as WSJT-X AD1CCty::lookup and Radio::effective_prefix: the
             call upper case; ending /MM or /AM: no entity. Operating suffixes are
             removed from the right while they are a digit, A, M, P, Q, R, QRP, FD, FF,
             AM, MM, LH, LT or LGT; of a remaining compound call the shorter side is the
             effective prefix (the left one when the right side is at least as long).
             When that differs from the call, an exact entry for the whole call wins.
             Otherwise the longest entry that starts the effective prefix, where an exact
             entry matches only the whole call. A KG4 call of length other than 3 or 5 is
             the United States entity (with that entry's overrides). The result is the
             entity with the entry's overrides: full name, primary prefix, continent, CQ
             and ITU zone, position. Shown name: WSJT-X abbreviated_entity_name, then the
             WAE entities shown as their DXCC (Bear Is., Shetland Is., AF Italy, Sicily,
             Vienna Intl Ctr, AF/EU Turkey), as with "Include extra WAE entities" off. */
    }
    attribute def DecodedEntity {
        doc /* #55 (CL-055-02). GET /receive/results adds to each decoded record whose
             sender call resolves the optional keys below; other records are unchanged. The
             sender call is the 'from' call, also a filled-in hash; of a nonstandard (i3=4)
             message its full call, or its filled-in hash when that comes second; of a
             DXpedition message its hashed call, for dxcc only because Band Activity names
             no sender for that form. A hash nobody heard ("<...>") and a free text have
             none. The keys:
             dxcc {name (shown name), cont, cq, itu, km (only with a profile locator:
             great circle in whole km to the entity position)} when the sender has an
             entity; flags {name: true ...} holding only the flags that are true, omitted
             when none is or the log is unreadable: new_call (the call, case-insensitive)
             and new_grid (the 4-character square of the message grid; none without a
             grid) not in the log; new_dxcc (entity full name, WAE entities by their own
             name as in WSJT-X), new_continent, new_cq_zone, new_itu_zone not in the log
             (from EntityOfCall of each logged call; a logged call without an entity
             counts for nothing); each with its _band form: not on this band in any mode
             (WSJT-X LogBook::match with highlight by mode off, its default; the
             strategy's filter is WstxStrategy::NewNeeded, #97). The worked set
             is rebuilt only when the log or the country table changes; the annotation
             runs off the async runtime. Band: the CAT dial
             band, else the operating selection band; without a band no _band flag is
             set. worked_status (notWorked as not_worked, workedOtherBandOrMode as
             worked_other_band_or_mode, workedThisBandAndMode as worked_this_band_and_mode,
             WorkedBeforeQuery of that band and the job's mode) on a standard message whose
             'from' is a concrete call, not a hash, when a band is known. The browser accepts exactly these optional keys and values; any other
             key or value refuses the page like any invalid record. */
    }
    attribute def CountryFileHttp {
        doc /* #55 (CL-055-03). GET /dxcc (read): {v:1, profile_id, boot_id, source
             "bundled"|"uploaded", version (the =VER marker or null), entities,
             upload_unreadable}; with ?call=<1..13 of A-Z 0-9 /, unencoded> also entity (the dxcc
             object of DecodedEntity or null), any other query 400 invalid_request call.
             PUT /dxcc {v, profile_id, boot_id, text} with exactly these keys, body at
             most 2 MiB: text null removes the upload (bundled again); a string of at most
             CountryFile::bytesMax bytes replaces it when it parses, else 400
             {error:{code:invalid_cty, field:text, line}}; other text 400 invalid_request
             text. Profile, boot, Origin and authorization checks as the log routes
             (wrong Origin 403, stale boot 409 state_conflict, revoked grant 401);
             a refusal changes neither the file nor the table. 200 is the new view.
             Environment-only mode: 404. */
    }

    // ---------------------------------------------------------------- displays
    attribute def OperatorDisplays {
        attribute utcClockText : String;
        attribute periodElapsedSeconds : Integer;
        attribute periodSeconds : Integer = 15;
        attribute transmitting : Boolean;
        attribute rxLevelDb : Integer[0..1];
        assert constraint progressBounds { periodElapsedSeconds >= 0 and periodElapsedSeconds < periodSeconds }
        assert constraint levelBounds { rxLevelDb == null or (rxLevelDb >= 0 and rxLevelDb <= 90) }
        doc /* D11 adopted. UTC clock HH:MM:SS (MW labUTC) from the server's UTC
             observation in the status stream, advanced locally between observations
             for display only; marked stale with the link; never a scheduling input.
             Tx progress (MW ~8388): #50, one period bar only, the QSO pane's NEXT bar
             (its width the elapsed part of the period, FT4-NOTE 7.5) with the countdown or,
             while #9 reports an active transmission, "▶ TX now" with the seconds left
             (#37, QsoPane NEXT); the top bar shows UTC only.
             The bar is red in a period of my Tx parity while Enable Tx is on and whenever
             transmitting is true, green otherwise (WstxOperatingLayout::QsoPane NEXT).
             StationPeriodClock (#50, operator 2026-11-02): the UTC clock, the bar and the
             countdown run on the station's UTC (the transmit owner's now_utc_ms, system
             clock plus the #43 correction, the clock the transmitter keys on), never on the
             browser's wall clock: each station observation (station.tick utc_ms and the
             ContactSnapshot utc_ms) gives offset = utc_ms - browser monotonic time at its
             receipt; the shown station time is the browser monotonic time plus the
             largest offset received in the last 20 s (a late delivery only lowers an
             offset); an offset more than 500 ms below that estimate is a backward step
             of the station clock (#43) and restarts the estimate at once. The bar is redrawn at least every 100 ms with no animated width
             change, so it restarts at 0 at each period start within 100 ms plus the
             link's one-way delay. Rx level meter (widgets/
             signalmeter.cpp, meterwidget.cpp): 0..90 dB, rxLevelDb = round(10 log10(mean(s^2))) with s
             the canonical receive samples scaled to 16-bit full scale (32768), over the
             last status interval, at most one value per second on the status link;
             labelled "high" above 85 dB and "low" below 15 dB (meterwidget.cpp ~61/~64 thresholds)
             in text and colour; null shows unavailable when audio is not running. #61
             CL-061-04: the station measures no level while on the air and for the rest of
             that Tx period (null then, "Tx · not measured" while transmitting); a level and
             its low/high entry refer to receive periods only. */
    }

    // ---------------------------------------------------------------- ADI log
    attribute def AdiLimits {
        attribute importBytesMax : Integer = 67108864;
        attribute importRecordsMax : Integer = 100000;
        attribute fieldCharactersMax : Integer = 1024;
        attribute fieldNameCharactersMax : Integer = 64;
        attribute importChunkBytesMax : Integer = 16384;
        attribute historyPageRecordsMax : Integer = 10;
        attribute historyPageBytesMax : Integer = 16384;
        doc /* Application admission limits (#10 text; not ADIF limits). Exactly at a
             limit is admitted, one over is refused: a file over importBytesMax or
             importRecordsMax, or a field name over fieldNameCharactersMax, refuses the
             whole update and publishes no record of it; a field value over
             fieldCharactersMax is a fault of that field only (UpdateLogbook). Inside a
             record only white space is permitted between a field value and the next
             tag; any other text there is a lengthMismatch fault of the field before it
             (an inexact LEN is never silently truncated: that value is not taken; the
             stored log refuses such a file, UpdateLogbook judges the field as below;
             Log4OM 2.42 writes CNTY values longer than their LEN). A logger export of about 27,000 QSOs with about 60
             fields each (Log4OM 2: about 28 MB) is inside these limits. The stored log is
             not limited by one update's record count. */
    }
    enum def AdiError {
        enum malformed; enum lengthMismatch; enum unsupportedCharacter; enum fieldTooLong;
        enum tooManyRecords; enum tooLarge; enum missingRequiredField; enum invalidValue;
        enum integrityMismatch;
    }
    action def UpdateLogbook {
        in importId : String;
        in totalBytes : Integer;
        in sha256 : String;
        out added : Integer;
        out present : Integer;
        out confirmed : Integer;
        out skipped : Integer;
        out error : AdiError[0..1];
        doc /* #10 operator request 2026-11-03 ("updating the logbook"): consolidate the
             log of another logger, exported as ADIF ADI (for example Log4OM 2), into
             the station's contact log, so one log without duplicates feeds
             worked-before, DXCC and grid status. Settings > Logging & Reporting >
             "Update logbook from ADIF": the operator picks the file and presses Update
             logbook. It is the one ADI import of the station: it replaces the former
             ImportAdi and retires its all-or-nothing conflict rule and its verbatim
             unknown fields (decision on #10: one function for any logger; a repeated
             update from a grown export adds only what is new).
             File (any ADIF 3.x ADI writer): UTF-8, a leading byte order mark ignored;
             an optional header (any text, such as '#' banner lines, and fields) ended
             by <EOH>; records end <EOR>; tags case-insensitive <NAME:LEN[:TYPE]> with
             exact LEN in characters; only white space between the fields of a record,
             see AdiLimits. Header fields are not stored; the header PROGRAMID, when it
             is a token of 1..32 letters, digits or '-', is the source marker, else ADIF.
             Refused as a whole, publishing nothing, with error {code,record,field}:
             integrityMismatch (sha256 of the received bytes, checked first); bytes
             that are no UTF-8, or a control character other than TAB/CR/LF outside a
             field value (unsupportedCharacter); a broken tag or a missing <EOH> or
             <EOR> (malformed); a LEN past the end of the file (lengthMismatch);
             tooLarge; tooManyRecords; a field name over the limit (fieldTooLong).
             Per record, after that structural check:
             - Kept fields: only the LogRecord fields (CALL, GRIDSQUARE, MODE, SUBMODE,
               RST_SENT, RST_RCVD, QSO_DATE, TIME_ON, QSO_DATE_OFF, TIME_OFF, BAND,
               FREQ, STATION_CALLSIGN, MY_GRIDSQUARE, TX_PWR, COMMENT and the #24
               contest fields STX, STX_STRING, SRX, CONTEST_ID, SRX_STRING, CLASS,
               ARRL_SECT, STATE), the confirmation fields (LOTW_QSL_RCVD, LOTW_QSLRDATE,
               QSL_RCVD, QSLRDATE, QSL_RCVD_VIA, EQSL_QSL_RCVD, EQSL_QSLRDATE; #10,
               2026-11-04), a valid APP_WSTXRUST_CONTACT_ID, APP_WSTXRUST_SOURCE and
               APP_WSTXRUST_ACTIVITY (an invalid one is dropped). Every other field
               (names, addresses, e-mail, QSL sent and upload states, other APP_ fields) is
               not stored, so the update does not widen the personal data the station
               keeps.
             - A record is skipped, with reason {code,field}, when CALL, QSO_DATE
               (valid YYYYMMDD), TIME_ON (HHMM or HHMMSS) or MODE is missing
               (missingRequiredField) or invalid (invalidValue; unsupportedCharacter
               for a value that is not printable ASCII; fieldTooLong; lengthMismatch
               for text after its value), or when a kept
               field occurs twice in it (malformed).
             - An optional kept field whose value fails its domain (FREQ and TX_PWR
               positive decimals, GRIDSQUARE and MY_GRIDSQUARE 2/4/6/8 Maidenhead, BAND
               the ADIF enumeration, RST at most 16 characters, SUBMODE a token,
               STATION_CALLSIGN 1..32 letters, digits or '/', the #24 contest fields as
               SaveContact admits them in LogRecord (STX and SRX 1-4 digits, the others
               at most 32 printable characters without '<' and '>'; coordinator
               decision on #10, 2026-11-04), the confirmation fields their LogRecord
               enumerations and dates, a contact id a UUID, a
               source a token; every value printable ASCII and at most
               fieldCharactersMax, with no text after it) is left out of that record,
               which is still added;
               the summary lists it as dropped {code,field}.
             Values are stored as written (no case or mode rewriting): MODE FT4 and
             MODE MFSK with SUBMODE FT4 are both FT4 for consolidation and
             worked-before (effective mode: SUBMODE when MODE is MFSK, else MODE).
             Consolidation (the record is already present, counted present, nothing
             changes): a record whose APP_WSTXRUST_CONTACT_ID is stored or was added
             earlier from the same file; or a stored record, or an earlier added record
             of the same file, with the same CALL (case-insensitive), effective band
             (BAND, or without BAND the ADIF band of FREQ, or none) and effective mode,
             whose start (QSO_DATE + TIME_ON) is at most 120 s from this record's start
             (WSJT-X/ADIF practice: loggers differ in seconds and rounding). The stored
             (or earlier added) record wins, so the station's own records keep all their
             fields, except that its confirmation is upgraded (#10, operator 2026-11-04):
             for each of LoTW (LOTW_QSL_RCVD, LOTW_QSLRDATE), paper QSL (QSL_RCVD,
             QSLRDATE, QSL_RCVD_VIA) and eQSL (EQSL_QSL_RCVD, EQSL_QSLRDATE) whose status
             is Y or V in this record and not Y or V in the present one, the present
             record takes this record's status and, where this record has them, its date
             and via. A confirmation is only added, never removed or downgraded; Y and V
             are both confirmed and do not replace each other; nothing else changes. The
             upgraded stored records are replaced in place (their indexes kept) in the
             same atomic replace as the added records. Otherwise the record is added: a new contact id when it has
             none, APP_WSTXRUST_SOURCE the file's marker unless it carries one. Added
             records are appended in file order in one atomic replace of contacts.adi
             (as SaveContact); a failed replace adds none.
             Repeatable and incremental: updating again with the same or a grown export
             adds only the records not yet present; export then update of the station
             log adds none.
             Nothing leaves the station: no WstxUdp QSO Logged or Logged ADIF, no other
             forwarding or upload; only DirectLog and SaveContact send logged contacts
             (SaveContact resends a contact a logging program missed).
             Summary: added, present, confirmed (the present records whose confirmation
             this update upgraded), skipped, reasons (the skipped records grouped by
             {code,field} with count and first record index) and dropped (the dropped
             fields grouped likewise), each at most 16 groups in order of first
             occurrence (skipped is always the full count). The browser shows "Logbook
             updated: N added, M already present (C confirmations updated), K skipped"
             ("1 confirmation updated" for one) with the reasons and the
             dropped fields, or "Logbook not updated" with the error and its
             record/field.
             Retry identity: importId is a caller-chosen UUID. Reserving the same
             importId with identical totalBytes and sha256 returns the existing
             resource or its final result without a second effect; different values are
             state_conflict. One update per profile at a time; the resource is retained
             until the next reservation or restart. Chunks follow the
             WstxRecordingReceive import pattern: exact Content-Range, at most
             importChunkBytesMax each, in order. Bulk transfer yields to status/control
             and never delays HaltTransmit. Authorization: an operator action with the
             configuration access of the other log routes.
             Workload (#10): a 28 MB export of about 27,000 QSOs is consolidated within
             seconds of its last chunk, also when a rerun upgrades the confirmation of
             all of its records, and worked-before stays an index lookup
             (WorkedBeforeQuery). */
    }
    action def ExportAdi {
        doc /* GET /contacts/export.adi streams the whole profile log as ADIF 3.1.8 ADI:
             header with ADIF_VER 3.1.8, PROGRAMID WSTXRUST and CREATED_TIMESTAMP, then
             every stored record in storage order with its supported fields (LogRecord
             set, including the confirmation fields), its app fields in the LogRecord order
             and preserved unknown fields verbatim. Content
             type application/octet-stream with attachment filename contacts.adi; no
             content coding; streamed with backpressure behind status/control: the log
             as it is at the request (a snapshot that holds no lock, so a save or update
             during the export succeeds and appears in the next export), sent with chunked
             transfer and no Content-Length, the header with the first 128 records and then
             128 records per chunk, each formatted only when the connection takes it, so a
             log of about 27,000 QSOs is never built in memory as one document (#10,
             2026-11-04). Export then UpdateLogbook of the same file adds no record (all
             already present). */
    }
    action def ContactHistory {
        in cursor : Integer;
        in limit : Integer;
        doc /* GET /contacts?cursor=&limit= returns exactly
             {v:1,profile_id,total,cursor,next,more,records}; records are the stored
             records in append (storage) order with index cursor..; records are only
             appended, and a DirectLog replacement keeps its record's index, so indexes
             are stable. limit 1..10 (default 10),
             cursor 0..total (total returns an empty page), page at most 16384 encoded
             bytes. Each record is exactly {index,contact_id,call,gridsquare,mode,
             submode,rst_sent,rst_rcvd,qso_date,time_on,qso_date_off,time_off,band,freq,
             station_callsign,my_gridsquare,tx_pwr,comment,stx,stx_string,srx,contest_id,
             srx_string,class,arrl_sect,state,unknown_field_count} with
             absent values null, rendered literally (not the LogRecord confirmation
             fields; ExportAdi carries them). Read-only inspection; no edit or
             delete. */
    }

    // ---------------------------------------------------------------- wire contract
    enum def ContactRefusal {
        enum invalid_request; enum unsupported_version; enum unauthorized; enum forbidden_origin;
        enum wrong_profile; enum not_found; enum request_too_large; enum unsupported_media_type;
        enum state_conflict; enum stale_revision; enum busy; enum counter_exhausted;
        enum contact_active; enum no_contact; enum row_unavailable; enum row_not_standard;
        enum directive_not_answerable;
        enum invalid_call; enum invalid_grid; enum invalid_report; enum invalid_message;
        enum out_of_range; enum profile_incomplete; enum transmit_unavailable;
        enum redecode_unavailable; enum log_invalid_field; enum log_conflict;
        enum import_failed; enum storage_unavailable; enum snapshot_limit;
        enum tx_watchdog; enum operator_required; enum clock_not_synchronized;
    }
    enum def ContactAction {
        enum select_row; enum enter_dx; enum cancel; enum choose_next; enum edit_message;
        enum set_report; enum set_tx1_skip; enum set_tx4; enum set_frequency; enum set_hold_tx;
        enum set_parity; enum set_auto_seq; enum set_call_first; enum set_watchdogs; enum abort;
        enum set_activity;
        enum enable_tx; enum tune; enum redecode; enum open_log;
        enum reply; enum call_cq; enum call_dx; enum send_next; enum reset_repetitions;
        doc /* discard_review is retired (#41, no log review queue) and refused
             invalid_request with field action. */
    }
    item def ContactCommand :> WstxArchitecture::StationRequest {
        attribute v : Integer = 1;
        attribute profile_id : String;
        attribute boot_id : String;
        attribute command_id : String;
        attribute contact_revision : Integer;
        attribute commandAction : ContactAction;
        doc /* POST /contact/command, body at most 1024 UTF-8 bytes, exact keys
             {v,profile_id,boot_id,command_id,contact_revision,action} (commandAction is the JSON key action) plus exactly the
             parameters of its action (all required, nullable where stated):
             select_row {row:{source_id,job_id,generation,sequence},replace} plus the optional
             directive_confirmed boolean (WstxStrategy::DirectedCqRule; refused
             directive_not_answerable, 409 with error.reason in the browser's case);
             enter_dx {dx_call,dx_grid|null,replace}; cancel {};
             choose_next {slot:"tx1".."tx6"}; edit_message {slot,text};
             set_report {report}; set_tx1_skip {enabled}; set_tx4 {form:"rrr"|"rr73"};
             set_frequency {rx_hz|null,tx_hz|null} (null = unchanged; pointer actions use
             this with the PointerEffect result); set_hold_tx {enabled};
             set_parity {parity:"even"|"odd"}; set_auto_seq {enabled};
             set_call_first {enabled} (CallFirst);
             set_activity {activity:"none"|"na_vhf"|"eu_vhf"|"ww_digi"|"arrl_digi"|"field_day"|"rtty"|"hound",
             exchange?} (GridExchangeContest, ContestExchange, EuVhfExchange, HoundOperation);
             set_watchdogs {tx_calls,tune_seconds}; enable_tx {enabled,
             safety_revision|null} (safety_revision: the CL-022 safety revision shown in
             the snapshot transmit view; for enabled true a value different from the
             station's current revision is stale_revision with field safety_revision);
             tune {enabled, safety_revision|null, the key optional} (WstxTransmit::SetTune:
             Tune on with another revision than the station's, or none, is stale_revision
             with field safety_revision; Tune off needs none);
             the start actions (StartActions), each with safety_revision|null as enable_tx:
             reply {row, safety_revision} plus the optional directive_confirmed as
             select_row; call_cq {safety_revision}; call_dx {dx_call,dx_grid|null,replace,
             safety_revision}; send_next {slot,safety_revision};
             reset_repetitions {safety_revision};
             redecode {} (last completed interval of the current live
             job; no browser control sends it since #37); open_log {} (manual Log QSO:
             DirectLog of the current contact now).
             replace true is the explicit ChangeContact; false with an active contact is
             contact_active. command_id is a caller UUID: the server retains the last 16
             command receipts per boot; an identical body with a retained command_id
             returns 200 with the same receipt and no effect; a different body with it
             is state_conflict. contact_revision must equal the current revision
             (stale_revision otherwise), except cancel, enable_tx false and tune false,
             which are admitted with any earlier revision. Validation order is the
             WstxOperatingReceive S2 order (route, Origin, TLS/session, size/media/syntax,
             version/enums/UUIDs/safe integers, profile, boot/revision, capability,
             state). Transmit actions on a station without transmit capability, or
             without a current CL-022 grant (a plaintext profile), are
             transmit_unavailable; Enable Tx arms #9 with the confirmed CL-022 safety
             revision it carries (#9 itself refuses a changed revision, reported
             stale_revision with field safety_revision; no check-then-arm race). A transmit outcome refused without a #9 disarm
             (duplicateSequence) disarms with cause refused and is never resubmitted
             unchanged; the engine's own disarms are not shown as refusals. */
    }
    item def CommandReceipt :> WstxArchitecture::StationOutcome {
        attribute v : Integer = 1;
        attribute command_id : String;
        attribute contact_revision : Integer;
        attribute accepted : Boolean = true;
        doc /* 202 exactly {v:1,profile_id,boot_id,command_id,contact_revision,accepted:true},
             at most 384 bytes: accepted, not yet confirmed effect. Refusals use the
             existing envelope {error:{code,field}} with code a ContactRefusal and field
             the offending JSON key or null; nothing is changed by a refusal. */
    }
    item def ContactSnapshot :> WstxArchitecture::StationOutcome {
        attribute v : Integer = 1;
        attribute contact_revision : Integer;
        attribute snapshot_sequence : Integer;
        doc /* GET /contact returns 200 exactly
             {v:1,profile_id,boot_id,contact_revision,snapshot_sequence,monotonic_ms,
             utc_ms,transmit,settings,contact,log,watchdog}, at most 4096 encoded
             bytes (503 snapshot_limit otherwise, never truncated). transmit is #9's read
             view exactly {capability:"unsupported"|"unavailable"|"available",
             arm_state,last_disarm_cause,last_arm_cause,tune,pending_sequence,last_text,
             last_period_utc,halt_state,safety_revision,refusal} (last_arm_cause
             "operator", "auto" or null, WstxTransmit::TransmitArming; safety_revision the
             current CL-022 safety revision of the selected radio scope or null);
             settings exactly {auto_seq,call_first,tx1_skip,
             tx_calls,tune_seconds,rx_hz,tx_hz,hold_tx,parity,report,activity,exchange,
             serial} (exchange the ContestExchange text or null); contact null or
             exactly {id,origin,dx_call,dx_grid,report_sent,report_rcvd,exchange_sent,
             exchange_rcvd,state,next_slot,
             tx4,messages,start_utc,end_utc,saved,suggested_slot,last_rcvd,dialogue} (report_sent the
             report of the last transmitted Tx2/Tx3 rendered, null until one is sent;
             suggested_slot null or the slot AutoSequence would select after the latest
             counted partner message while Auto Seq is off, e.g. tx5 after their RR73 in
             rogerReport; the state and next slot do not change, the QSO pane offers it,
             and choose_next clears it; null outside replying..signoff, #11;
             last_rcvd null or exactly {text,snr,period_utc_ms,count}: the latest partner
             message to my call that the engine counted, or the selected row when it was
             addressed to me, with its rounded SNR or null, its period start (Unix ms) and
             how many consecutive counted messages had that identical text; null for a new
             contact; the QSO pane's last partner message, #37; dialogue (#37, operator
             2026-11-02) an array of at most 16 entries exactly {dir:"rx"|"tx",text,snr,
             period_utc_ms,count}, oldest first: "rx" each partner message the engine
             counted for this contact (as last_rcvd, including the selected row addressed
             to me) with its rounded SNR or null, "tx" each transmission of this contact
             whose audio started (the text as sent, snr null); a message equal in text to the
             newest entry of its dir (also across an entry of the other dir, #39: a partner
             repeating while I repeat keeps both Reps counting) increments that entry's
             count instead, except the first transmission after an operator Enable Tx
             from off, which opens a new entry; selecting a row of the current partner, or entering
             it again, keeps the dialogue, the Tx4 form, each slot's current text when it was already sent,
             also an edited one, and, once the
             current Tx2 or Tx3 text was sent, the report whatever the row's SNR (its
             period_utc_ms stays the first period; its snr becomes the repeat's SNR when
             that is not null, so it is the latest decode's, #60); beyond 16 the oldest entry is dropped;
             empty for a new contact and cleared by CancelContact)
             with messages an array
             of six strings or nulls (Tx1..Tx6, each at most 37 characters); saved true
             when contacts.adi holds the contact's record; log (DirectLog) null until a
             contact of this boot was logged, else exactly {contact_id,call,outcome,error}
             of the latest attempt: outcome saved (stored, replaced or already stored)
             with error null, or unsaved with error storage_unavailable (pending, retried),
             log_queue_full or log_invalid_field (not retried); watchdog exactly {tx_remaining_calls,
             tx_expired,tune_remaining_seconds,busy_with,paused_calls}; tx_remaining_calls is the Tx
             watchdog's only (#97, #91: limit minus the counted repetitions, TxWatchdog), or null
             while the Tx watchdog does not bound the contact (a strategy or contest run's own
             contact while the run is attended, WstxStrategy::StrategyWatchdog), when the browser
             shows no WD (the run's leave label instead, WstxStrategy::LeaveCountLabel; "WD:∞" is
             gone); busy_with and paused_calls per BusyPartner. contact_revision advances on every
             accepted command and every server-side sequence/transmit/watchdog change;
             snapshot_sequence also on clock-free material changes. No content coding:
             /contact, /contacts and /contacts/* are not in the six-route
             WstxHttpContentCoding::ExactCompressedGetRoute allowlist and stay identity. */
    }
    item def ContactStateEvent {
        attribute v : Integer = 1;
        attribute 'type' : String = "contact.state";
        doc /* New versioned WebSocket event on the existing wstx.v1 socket, exactly
             {v:1,type:"contact.state",data:{profile_id,boot_id,contact_revision,
             snapshot_sequence,monotonic_ms,utc_ms,changed}}, at most 2048 bytes, sent when
             the GET /contact snapshot of this peer changes or its contact_revision does (then
             with an empty changed, so the next command has the revision), coalesced to at most one per
             second per peer and always sent within 1 s of a change; below Detailed a change
             of only watchdog.tune_remaining_seconds at most once per 5 s. changed (#10
             2026-11-06, operator rule 2026-11-04): on a peer's first event every field of
             transmit, settings, contact, log and watchdog, null too; later only the
             changed fields, of transmit, settings and watchdog only the changed members,
             of the same contact (id) only the changed members. A contact's dialogue goes
             with dialogue_from, the index of its first row, and only the rows the peer
             lacks: all rows when an earlier row changed; rows over the frame budget follow
             on the next tick. The always-loaded browser client holds the snapshot from these
             events from the socket's first on, so a contact client loading later misses
             none, and shows a snapshot_sequence not older than its own; it reads GET /contact once per socket, with one
             pending GET per browser. After its own command it shows the command's reply
             (accepted, or the refusal with its code) and reads nothing: the next command goes
             at once with the newer of the held and the last receipt's contact_revision, and
             GET /contact is read only when no contact.state holds the receipt's revision
             within 5 s; after a stale_revision refusal of contact_revision the explicit
             gesture (double-click, Reply, CQ) waits up to 2.5 s for a newer revision before
             its retry, outside the command order, after one of another field
             (safety_revision) or an unknown outcome it reads at once. A choice made from the
             held state (Log QSO, a row's selection, CQ) waits for a command and result still
             on their way; Esc and Abort QSO never wait, and after them nothing an earlier
             gesture queued (its retry, its Enable Tx) is sent (#10). It is not a StatusReply:
             station.status stays exactly {v,type,id,data{version,radio}}. Control and
             status keep priority over it as over optional visualization. */
    }
    item def StationTickEvent {
        attribute v : Integer = 1;
        attribute 'type' : String = "station.tick";
        doc /* New versioned WebSocket event, exactly
             {v:1,type:"station.tick",data:{profile_id,boot_id,utc_ms,period_ms,
             transmitting,rx_level_db}}, at most 224 bytes (the exact keys with two UUIDs
             and a 13-digit utc_ms already need 220; corrected from 192 by the #10
             implementation, review required). Rate per peer by its display
             subscription: Detailed 1 per second; Thin and Off 1 per 5 s; plus at most one
             extra event per transmit start/stop. A peer that never chose a display
             subscription (a bare status observer) receives neither event. The browser interpolates the UTC clock
             and Tx progress locally from utc_ms with its monotonic clock between ticks
             (display only); rx_level_db shown is the latest tick value. Budget: Off idle
             with two clients adds at most 2 x (224 + 2 WS + 29 TLS + 160 accounted
             TCP/ACK) / 5 s = 166 B/s per direction, so the status-only idle total stays
             within WstxStationProtocol::ThinLinkBudget 1000 B/s; Thin stays within the
             existing 3000 B/s live envelope. Both are targets judged from
             WstxStationProtocol::LinkTrafficLog (#80). */
    }
    attribute def ContactWire {
        doc /* Routes of WstxContact (selected-profile mode only; environment-only mode
             404 not_found): GET /contact; POST /contact/command; POST /contacts (SaveContact:
             exactly {v,profile_id,boot_id,command_id,record}, body at most 8192 bytes so
             that a 1024-character comment fits with worst-case JSON escaping;
             201 {v:1,contact_id,outcome:"saved"}, 200 alreadySaved, 409 log_conflict,
             400 log_invalid_field with field, 503 storage_unavailable leaving the record
             unsaved; the record may carry app_wstxrust_activity, refused 400
             log_invalid_field field record.app_wstxrust_activity outside its values); GET /contacts (ContactHistory); GET /contacts/export.adi
             (ExportAdi); POST /contacts/imports {v,profile_id,boot_id,import_id,
             total_bytes,sha256} 201/200 reserve; PUT /contacts/imports/{id} chunks;
             GET /contacts/imports/{id} exactly {v:1,id,state,received_bytes,total_bytes,
             added,present,confirmed,skipped,reasons,dropped,error} with reasons and dropped arrays
             of {code,field,count,record} and error null or {code,record,field}; the
             completing chunk answers 201 with that view, a refused update 422
             import_failed (UpdateLogbook); POST /transmit/halt (WstxTransmit::HaltTransmit).
             All use the existing HTTP/TLS authentication, exact Origin on mutations,
             JSON media rules and error envelope; the 1024-byte body cap applies except
             the stated 8192-byte save body and 16384-byte
             update chunks. Mutations are never
             replayed automatically; reconnect reads GET /contact first. MCP uses the
             same station operations. */
    }

    dependency contactOwner from Contact to WstxArchitecture::QsoAndLogging;
    dependency qsoSettingsOwner from QsoSettingsFile to WstxArchitecture::QsoAndLogging;
    dependency qsoSettingsClause from QsoSettingsFile to WstxRequirements::'CL-110-01';
    dependency transmitBoundary from TransmitSubmission to WstxTransmit::TransmitRequest;
    dependency transmitOwner from TransmitSubmission to WstxArchitecture::TransmitService;
    dependency contactPromise from AutoSequence to WstxRequirements::'FR-007';
    dependency transmitPromise from TxWatchdog to WstxRequirements::'FR-008';
    dependency busyPartnerClause from BusyPartner to WstxRequirements::'CL-097-06';
    dependency busyWatchdogClause from TxWatchdog to WstxRequirements::'CL-097-06';
    dependency logPromise from LogRecord to WstxRequirements::'FR-011';
    dependency directLogClause from DirectLog to WstxRequirements::'CL-010-04';
}
