package WstxRecordingReceive {
    private import ScalarValues::*;
    private import WstxOfflineDecode::Mode;
    private import WstxOfflineDecode::Settings;
    private import WstxOfflineDecode::ResultRecord;
    private import WstxProfileRecordings::StartImportBody;
    private import WstxProfileRecordings::ImportView;
    doc /* Implementation contract from authoritative contract 4.4/6.4/12.6. Original Thin/recording and Detailed refinement implementations with executable
         verification companions exist;
         actual run/review/acceptance evidence belongs to issue #6. Existing
         usages only, no new deployment/universal job manager/TX authority.
         Shared RustFFT6.4.1 primary API https://docs.rs/rustfft/6.4.1/rustfft/,
         https://docs.rs/rustfft/6.4.1/rustfft/trait.Fft.html and
         https://docs.rs/rustfft/6.4.1/rustfft/struct.FftPlannerScalar.html.
         Independent DFT/math/oracles remain independent case expectations and direct math, not library output. */
    enum def ReceiveState { enum running; enum cancelling; enum completed; enum cancelled; enum failed; }
    enum def DisplayProfile { enum off; enum thin; enum detail; }
    enum def ReceiveKind { enum spectrum; enum live; }
    enum def ErrorCode {
        enum forbidden_origin; enum unauthorized; enum unsupported_media_type;
        enum request_too_large; enum invalid_request; enum unsupported_version;
        enum wrong_profile; enum state_conflict; enum not_found; enum busy;
        enum invalid_state; enum invalid_recording; enum unsupported_audio;
        enum recording_limit; enum storage_unavailable; enum upload_timeout;
        enum cancelled; enum no_recording; enum generation_exhausted;
        enum recording_unavailable; enum unavailable; enum counter_exhausted;
        enum invalid_samples; enum decode_limit; enum decode_failed;
    }
    attribute def Limits {
        attribute blockSamples : Integer = 4096;
        attribute spectrumBlocks : Integer = 2;
        attribute workersPerStation : Integer = 1;
        attribute pendingJobs : Integer = 0;
        attribute fftSize : Integer = 2048;
        attribute detailFftSize : Integer = 4096;
        attribute detailHopFrames : Integer = 480;
        attribute commonHistorySamples : Integer = 8192;
        attribute defaultDisplayRangeDb : Integer = 30;
        attribute minDisplayRangeDb : Integer = 10;
        attribute maxDisplayRangeDb : Integer = 80;
        attribute detailBins : Integer = 1024;
        attribute detailRowFrames : Integer = 2400;
        attribute detailRows : Integer = 600;
        attribute detailIntervalMs : Integer = 200;
        attribute detailEventBytes : Integer = 2048;
        attribute detailBase64Chars : Integer = 1368;
        attribute outboundWriteBufferBytes : Integer = 4096;
        attribute controlHeadroomBytes : Integer = 1052;
        attribute hopFrames : Integer = 256;
        attribute displayBins : Integer = 128;
        attribute browserRows : Integer = 120;
        attribute pendingFramesPerPeer : Integer = 1;
        attribute pendingRepaint : Integer = 1;
        attribute displayIntervalMs : Integer = 1000;
        attribute checkpointMs : Integer = 50;
        attribute replayCancelReleaseMs : Integer = 250;
        attribute finalProcessingMs : Integer = 1000;
        attribute controlBytes : Integer = 1024;
        attribute eventBytes : Integer = 1024;
        attribute thinBytesPerSecond : Integer = 3000;
        attribute offBytesPerSecond : Integer = 1000;
        attribute statusDisplayMs : Integer = 2000;
        attribute pageBytes : Integer = 1536;
        attribute pageRecords : Integer = 1;
        attribute pollMs : Integer = 2000;
        attribute windowFrames : Integer = 360000;
        attribute advanceFrames : Integer = 180000;
    }
    attribute def DisplayLevels {
        attribute blackDbfs : Integer = -85;
        attribute rangeDb : Integer = 50;
        attribute sensitivityDb : Integer = 0;
        attribute speedMultiplier : Real = 1;
        attribute flatten : Boolean = false;
        attribute spectrumLine : Boolean = false;
        assert constraint localSliders { sensitivityDb >= -30 and sensitivityDb <= 30 and speedMultiplier >= 0.5 and speedMultiplier <= 8 }
        assert constraint displayRange { rangeDb >= 10 and rangeDb <= 80 and blackDbfs == -85 }
        doc /* #54 (CL-054-02), as WSJT-X's Wide Graph: a fixed dBFS-to-colour mapping; no level
             follows the signal over time and nothing resets it on a new job, source or profile.
             B is the fixed reference -85 dBFS. Sensitivity g (WSJT-X Zero, -30..+30, default 0)
             moves the scale: effective black E=clamp(B-g,-120,-R). Range R (WSJT-X Gain, a slider
             10..80 dB, default 50) is the span [E,E+R]. Speed sets 10*speedMultiplier CSS px per
             source second (default 1: about two FT8 periods in the default height); fixed source
             intervals move down independent of history length, clip at bottom; unobserved pixels
             dark/no-measurement. Sensitivity, Range, Speed, Flatten and the spectrum line are
             per-browser settings that apply at once and persist in browser storage. Flatten
             (default off, WSJT-X flat4 equivalent) subtracts per row the lower envelope across
             frequency (20th percentile of 32 blocks, linearly interpolated) and adds back its
             median: it evens out the passband shape, never a level change over time; the readout
             keeps the original native levels. Original calibrated levels unchanged.
             Rounding, exact RGB palette, ruler/readout/geometry and all actions
             remain normative in PresentStation/CalculateSpectrum source contract. */
    }
    attribute def Correlation {
        attribute profile_id : String;
        attribute boot_id : String;
        attribute source_id : String;
        attribute job_id : String;
        attribute generation : Integer;
        doc /* Lowercase hyphenated UUIDs,never path/name/port. Station generation !=
             sample position/config revision/request ID/frame sequence; match full tuple
             before publication. New replay allocates job+generation,source unchanged. */
        assert constraint safeGeneration { generation >= 0 and generation <= (900719925 * 10000000 + 4740991) }
    }
    attribute def ReceiveContext {
        attribute profile_id : String;
        attribute boot_id : String;
        attribute source_id : String[0..1];
        attribute job_id : String;
        attribute generation : Integer;
        assert constraint safeGeneration { generation >= 0 and generation <= (900719925 * 10000000 + 4740991) }
        doc /* Opening live job may lack source only until initial provider epoch ACK.
             Recorded spectrum and acknowledged live jobs require their source UUID.
             This pending context never permits publication. Correlation remains the
             REQUIRED full source/job/generation tuple for every frame/result page. */
    }
    attribute def SourceDescriptor {
        attribute schema_version : Integer = 1;
        attribute profile_id : String;
        attribute boot_id : String;
        attribute source_id : String;
        attribute rate_hz : Integer;
        attribute channel : String = "mono_real";
        attribute total_frames : Integer[0..1];
        attribute utc_anchor : String[0..1];
        doc /* Immutable source lifetime. Recording12000Hz,known1..1440000frames,UTCnull;
             no filename timestamp. #8 settles live rates/clock/UTC/discontinuity before
             device code. Optional UTC separate from sample clock,not hardware support. */
        assert constraint schemaRate { schema_version == 1 and rate_hz > 0 }
    }
    item def SampleBlock :> WstxArchitecture::SampleBlock {
        attribute source : SourceDescriptor;
        attribute first_frame : Integer;
        attribute samples : Real[1..4096];
        attribute discontinuity : Boolean;
        attribute end_of_stream : Boolean;
        assert constraint nonnegativePosition { first_frame >= 0 }
        doc /* Finite f32 mono real,signedPCM16/32768 exactly. Arc<[f32]> or equivalent
             immutable shared owner;borrowers cannot mutate,producer reuse waits for
             last reference release. #6 spectrum path retains<=2blocks incl producer/
             consumers,no whole-file float array/backlog. #7 separately bounds modem
             history,not restricted to2blocks. Recordings start0,contiguous positions,
             discontinuityfalse,EOS last nonempty block. Semantic incompatible changes
             need coordinated new version. Unit conversion !=AGC/preprocessing/resampling. */
    }
    item def ReceiveJob :> WstxArchitecture::ProcessingRequest {
        attribute schema_version : Integer = 1;
        attribute correlation : ReceiveContext;
        attribute kind : ReceiveKind;
        attribute 'state' : ReceiveState;
        attribute processed_frames : Integer;
        attribute error : ErrorCode[0..1];
        attribute cancelRequested : Boolean;
        assert constraint progress { processed_frames >= 0 and ((kind == ReceiveKind::spectrum and processed_frames <= 1440000) or (kind == ReceiveKind::live and processed_frames <= (900719925 * 10000000 + 4740991))) }
        doc /* Shared receive lifecycle: recorded spectrum below and continuous live mode
             through WstxRadioIO/WstxModemDecode. One import OR recorded spectrum OR live receive,
             one worker/no pendingjobs; no CPU/file work holding state/profile lock. New
             generation on import/replay,refuse ceiling not wrap. Cancellation invalidates
             publication before ack;terminal progress remains until nextjob. No TX scope. */
    }
    attribute def JobView {
        attribute id : String;
        attribute source_id : String[0..1];
        attribute generation : Integer;
        attribute kind : ReceiveKind;
        attribute 'state' : ReceiveState;
        attribute processed_frames : Integer;
        attribute error : ErrorCode[0..1];
        doc /* source_id null only for live opening before first ACK; recorded source and all publication tuples remain required UUIDs. */
    }
    item def SpectrumFrame :> WstxArchitecture::ProcessingResult {
        attribute v : Integer = 1;
        attribute boot_id : String;
        attribute source_id : String;
        attribute job_id : String;
        attribute generation : Integer;
        attribute sequence : Integer;
        attribute first_frame : Integer;
        attribute end_frame : Integer;
        attribute levels : Integer[128];
        assert constraint interval { sequence >= 0 and first_frame == 12000 * sequence and end_frame > first_frame and end_frame <= first_frame + 12000 }
        doc /* Exact envelope v1,type spectrum.frame,data with fields above except v;
             levels each0..120,q-120dBFS. end=min(first+12000,source_frames). sequence0
             per replay,advances despite droppedrows. Immutable producer-owned frame,
             <=1replaceable pending/peer,<=1send/s;browser120rows*128values,1pendingpaint.
             groupb[b*23.4375,(b+1)*23.4375)Hz. Ignore obsolete tuple/socket callbacks,
             show gaps,clear newsource/job. Required decode results never share drop rule. */
    }

    item def DetailedSpectrumFrame :> WstxArchitecture::ProcessingResult {
        attribute v : Integer = 1;
        attribute boot_id : String;
        attribute source_id : String;
        attribute job_id : String;
        attribute generation : Integer;
        attribute sequence : Integer;
        attribute first_frame : Integer;
        attribute end_frame : Integer;
        attribute levels_b64 : String;
        assert constraint interval { sequence >= 0 and first_frame == 2400 * sequence and end_frame > first_frame and end_frame <= first_frame + 2400 and end_frame <= (900719925 * 10000000 + 4740991) }
        doc /* Exact spectrum.detail.frame envelope, <=2048 UTF8bytes; same current UUID/
             safe-integer tuple as Thin. Canonical padded standard RFC4648 base64 exactly
             1368chars decodes1024 bytes each0..120. Unknown/missing fields,
             noncanonical encoding, bad bounds/identities/socket are rejected atomically.
             Retain one latest immutable frame per profile in existing station state;
             per peer one replaceable selected frame, not two queues or another job. */
    }

    item def RecordedDetailedSpectrumFrame :> DetailedSpectrumFrame {
        assert constraint recordedSequence { sequence < 600 }
        doc /* Same wire shape. Finite recording-only bound; live uses safe common
             frame domain and actual capture counters, not this finite subtype. */
    }

    attribute def StartReplayBody :> StartImportBody { attribute recording_id : String; }
    enum def HttpMethod { enum get; enum mutation; }
    attribute def HttpResponsePolicy {
        attribute cacheControl : String = "no-store";
        attribute corsAllowed : Boolean = false;
        attribute jsonMediaType : String = "application/json";
        doc /* contract 12.6: UTF-8 JSON except raw WAV input. No CORS permission is emitted.
             JSON accepts optional UTF-8 charset as12.5. JSON schemas are exact:
             reject duplicate/unknown/missing keys. */
    }
    attribute def HttpErrorDetail {
        attribute code : ErrorCode;
        attribute 'field' : String[0..0];
        doc /* Exact members code and field. field is JSON null; code is the stable
             declared error code, never reflected request input. */
    }
    attribute def HttpErrorBody {
        attribute error : HttpErrorDetail;
        doc /* Exact UTF-8 wire shape {"error":{"code":"...","field":null}}. */
    }
    calc def OriginAllowed {
        in method : HttpMethod;
        in originHeaderCount : Integer;
        in suppliedOriginEqualsSelectedOrigin : Boolean;
        return allowed : Boolean =
            (method == HttpMethod::get and originHeaderCount == 0) or
            (originHeaderCount == 1 and suppliedOriginEqualsSelectedOrigin);
        doc /* contract 12.6: GET alone permits absent Origin. Every mutation requires
             one exact Origin even on loopback. Repeated Origin is refused. */
    }
    calc def HttpAccessStatus {
        in selectedProfileModeAndKnownRoute : Boolean;
        in originAllowed : Boolean;
        in tls : Boolean;
        in selectedProfileSessionValid : Boolean;
        return status : Integer = if not selectedProfileModeAndKnownRoute ? 404 else
            if not originAllowed ? 403 else
            if tls and not selectedProfileSessionValid ? 401 else 200;
        doc /* Precedence is mode/route, Origin, TLS session, then payload/resource
             checks in HttpValidation. TLS requires its selected profile's session
             on every recording route. 200 means admitted, not a final route result. */
    }
    attribute def HttpValidation {
        attribute selectedProfile : Boolean;
        attribute originAllowed : Boolean;
        attribute authenticated : Boolean;
        attribute responsePolicy : HttpResponsePolicy;
        attribute mediaAllowed : Boolean;
        attribute bodyBounded : Boolean;
        attribute schemaValid : Boolean;
        attribute versionSupported : Boolean;
        attribute sameProfile : Boolean;
        attribute sameBootGeneration : Boolean;
        attribute resourceKnown : Boolean;
        attribute stateAllowed : Boolean;
        doc /* Validation order: mode/route existence; Origin (403 forbidden_origin); TLS auth
             (401 unauthorized); content type/encoding (415 unsupported_media_type); declared or
             observed body bound (413 request_too_large, transport rejection may occur earlier);
             exact JSON/UUID/safe-integer/version schema (400 invalid_request/unsupported_version);
             profile mismatch (403 wrong_profile); boot/generation mismatch (409 state_conflict);
             resource existence (404 not_found); busy/state compatibility (409 busy/invalid_state);
             file structure (422 invalid_recording); supported PCM capability (422 unsupported_audio);
             frame/duration/chunk limit (422 recording_limit); I/O/cleanup (503 storage_unavailable).
             Malformed/missing/duplicate Content-Range is400 invalid_request; incorrect byte offset
             or changed total is409 state_conflict. An import total above the file cap is413
             request_too_large. A stalled/expired import is408 upload_timeout, explicit cancel is409 cancelled on an
             in-flight PUT; completed DELETE still returns200. A missing recording is409 no_recording;
             generation ceiling is409 generation_exhausted. Syntactic UUID errors are400; foreign
             well-formed UUIDs are404 except explicit profile_id mismatch. Errors do not echo input.
             Input progress is bytes received/declared Content-Range total while receiving; before
             the first chunk show awaiting upload rather than a fabricated percent. Validation/commit states are distinct from completed. */
    }
    action def CancelImport {
        in importId : String;
        out resource : ImportView;
        doc /* Cancellation invalidates publication/commit authorization before its HTTP acknowledgement;
             accepting that operation and constructing its response take at most250ms locally,
             excluding network transit. Normal cleanup finishes within1s in isolated Windows tests.
             After an I/O error or5s cleanup deadline, publish failed/storage_unavailable and set
             storage_error; keep the pending files/handles quarantined and retain the one occupied
             operation/worker slot. Refuse further import/replay with503 storage_unavailable until
             cleanup actually succeeds or restart reconciles the directory. Do not claim deletion,
             start replacement workers or revert an already committed source. A blocked OS call may
             finish later, but its invalidated token cannot commit; final release clears storage_error
             only after real cleanup. Status/profile/settings and cancellation observation stay usable.
             Restart attempts cleanup once before enabling imports; failure keeps the degraded state.
             These are bounded application outcomes, not a claim to interrupt a blocked Windows I/O
             system call. A commit already begun is reconciled via snapshot, not cancelled. */
    }
    action def ReplaySpectrum {
        in request : StartReplayBody;
        out job : ReceiveJob;
        out frames : SpectrumFrame[*];
        out detailedFrames : RecordedDetailedSpectrumFrame[*];
        doc /* **Receive lifecycle.** One active import OR replay per station, one CPU worker,
             no pending job queue; concurrent start gets `busy`. State owner transitions and token
             checks serialize; CPU/file work does not hold the state owner or profile-settings lock.
             A replay job has schema 1, profile/boot/source/job UUIDs, station generation (`u64`,
             wire-safe 0..9,007,199,254,740,991), kind `spectrum`, immutable settings, processed frame
             count and cooperative cancellation. #7 adds a separately approved decode settings kind
             using the same receive lifecycle. States are `running`, `cancelling`, `completed`,
             `cancelled`, `failed`; terminal progress remains in the snapshot until another job starts.
             Starting an import or replay allocates a fresh station generation; starting replay also
             allocates a fresh job UUID. Cancellation invalidates publication before returning its
             acknowledgement; every receive terminal transition follows worker release. For a
             current running job with no accepted cancellation, a processing failure remains
             nonterminal while the worker is held, then transitions to failed after release;
             it cannot become completed even if source EOS/completion is also observed. Completion
             requires source completion, worker release and absence of processing failure. These
             rules preserve the existing serialized cancellation/state ownership, rather than adding
             another cancellation priority policy. Do not reuse a generation
             on wrap; refuse new work with `generation_exhausted`. Every publication matches current
             profile/boot/source/job/generation. A prior job's completion/frames cannot replace the
             current snapshot. Source UUID is the persistent recording UUID, not a replay identity.
             Receive cancellation does not govern transmit authority or delay #9 halt.

             Spectrum replay in #6 is explicit, server-paced at source time (1x) for inspection,
             not speaker playback and not a radio operation. This pacing applies only to spectrum
             jobs; #7 must settle its offline decode pacing/runtime and bounded modem working history
             independently, using the same immutable source/sample and receive job identities. Completion occurs within1s after the source duration on the stated Windows workload,
             including final processing. Another browser may observe/cancel the same station-owned job. Browser
             closure/link loss removes its subscription; it does not cancel an accepted replay.
             Cancellation checks are at most 50 ms apart and worker release/terminal state occurs
             within 250 ms after cancellation is accepted, measured on the recorded Windows test PC
             with four profile processes and one active worker each. No hardware/global CPU-count
             auto-allocation is introduced. The UI reports the one-worker-per-station budget. */
    }
    action def CancelReceive {
        in jobId : String;
        out 'state' : ReceiveState;
        doc /* DELETE /recording/jobs/{id},nobody;running->cancelling,publication invalid
             before200{v1,id,generation,state};checkpoints<=50ms,terminalcancelled+release
             <=250ms onfourprocessWindowsworkload. TerminalDELETE unchanged,unknown/
             oldboot/foreignjob404,never cancels differentjob. terminalprogressretained. */
    }
    action def CalculateSpectrum {
        in samples : SampleBlock[*];
        out rows : SpectrumFrame[*];
        out detailedRows : DetailedSpectrumFrame[*];
        doc /* **Independent display definition (Thin, unchanged).** For 12 kHz input, use 2,048 real samples per
             window, hop 256 source frames, periodic Hann `w[n]=(1-cos(2*pi*n/2048))/2`; windows start
             at source frames 0,256,... while their start is before EOS. Right-pad the final partial
             windows with zeros, retaining actual source end in metadata. DFT convention is
             `X[k]=sum(x[n]*w[n]*exp(-i*2*pi*k*n/2048))`. Peak amplitude is `2*abs(X[k])/sum(w)` for
             positive interior bins and `abs(X[0])/sum(w)` for DC. Level is
             `20*log10(max(amplitude,10^(-120/20)))`, clipped to [-120,0] dBFS. This is calibrated
             peak-amplitude dBFS, not power density, SNR or receiver RF power. FFT output must agree
             with this independent definition regardless of the jointly selected provider. The joint
             technical selection is RustFFT **6.4.1** for both #6/#7: complex unnormalized
             forward negative-sign/inverse positive-sign transforms, DC-first ordering and caller-owned
             scaling. Use CPU `FftPlanner<f32>` for the normal path; retain an independently checked
             `FftPlannerScalar<f32>` portable path. A worker copies/window-converts source data into
             its own complex buffer, obtains `get_inplace_scratch_len()` for the plan and reuses
             worker-owned scratch with `process_with_scratch`; neither mutable buffer aliases the
             original immutable samples. #6 uses N=2048 for Thin and N=4096 for Detailed; #7 owns its supported transform sizes and
             bounded modem working history. Plan once per needed size/worker, never per display row;
             check lengths before processing so invalid input cannot reach a panic precondition.
             No generic FFT wrapper or additional RealFFT dependency is needed. This is the central
             owned dependency contract; the implementation declares RustFFT once in the server crate.
             The independent math/oracles remain this definition, rather than library output. Normative primary API: [RustFFT6.4.1 normalization/output order](https://docs.rs/rustfft/6.4.1/rustfft/),
             [`Fft` scratch/buffer contract](https://docs.rs/rustfft/6.4.1/rustfft/trait.Fft.html) and
             [`FftPlannerScalar`](https://docs.rs/rustfft/6.4.1/rustfft/struct.FftPlannerScalar.html).
             The explicit DFT formula above fixes sign/scaling independently of the provider.

             Expose 128 groups over [0,3000) Hz: group b is bins 4b..4b+3, each original bin separated
             by 12000/2048 Hz; group interval is [b*23.4375,(b+1)*23.4375) Hz. Retain maximum amplitude
             before converting to dBFS. One waterfall row covers each one-second source interval
             [j,j+1), shortened at EOS, taking maxima of windows whose start falls in that interval.
             Consequently window support can extend into the next interval; this smoothing is part
             of the time oracle. The spectrum is the same row's one-second peak hold. Quantize level
             as `floor(clipped_dBFS+120+0.5)` to integer 0..120; decoded level is q-120 dBFS with at
             most 0.5 dB quantization error. A 0.5-amplitude coherent tone has approximately -6.0206
             dBFS before PCM quantization, not a code-generated golden value. Silence is -120 dBFS.
             Label frequency in Hz, time relative to recording start in seconds and level in dBFS.
             Show gaps on skipped row sequences; never interpolate a missing row as observed signal.
             Browser retains at most 120 rows of 128 values; replacing the source/job clears history.

             **Detailed display definition.** Detailed is a fast-link profile with 1,024 native
             frequency bins, not a sharpened/resampled Thin image. For 12 kHz input use N=4096,
             hop480 (40ms), periodic Hann with denominator4096 and the same DFT sign, amplitude/DC rule,
             dBFS floor/clipping and integer quantization as Thin with N substituted throughout.
             Expose k=0..1023 at center frequency k*2.9296875 Hz, covering [0,3000) Hz without
             frequency pooling. The displayed bin's frequency cell is [k*2.9296875,(k+1)*2.9296875)
             Hz; this is display geometry, not a claim that the Hann response has rectangular support.
             A row j covers source frames [2400*j,min(2400*(j+1),source_frames)); use global
             window starts0,480,... strictly before EOS. Every nonempty row includes its start2400*j,
             so a full row has exactly five windows and a partial final row has one through five.
             For each bin k, let A[m,k] be each window's calibrated peak-amplitude estimate above;
             compute P[k]=sum(A[m,k]^2)/M over the M actual window starts in this row, then
             L[k]=clamp(10*log10(max(P[k],1e-12)),-120,0) and q=floor(L[k]+120+0.5).
             There is no frequency pooling, logarithmic averaging or maximum hold in Detailed.
             For source_frames2401, row1=[2400,2401) includes only start2400: the lone sample
             multiplies Hann w[0]=0 and the row is legitimately silence, not missing/fabricated data.
             Right-pad partial windows at EOS; window support is 4096/12000 seconds, can cross row
             boundaries and MUST be stated in the legend alongside 2.9296875 Hz bins and 0.2 s rows.
             The spectrum shows the latest row's levels. Row sequence starts0 and advances even
             when output is skipped; send at most5 rows/s/peer, paced against the source clock.
             Thin continues its exact N2048/four-bin/one-second definition and event schema.

             One replay/source reader and one existing station-owned worker produce both profiles
             concurrently; selecting Detailed never starts another job or reparses/reloads the file.
             Reuse RustFFT6.4.1 with one plan/buffer/scratch per needed size, the existing sample
             parser/immutable boundary, identities and cancellation checks. Keep at most two source
             blocks plus at most8192 f32 samples in a common bounded history, the two bounded FFT
             workspaces (2048 and4096 complex elements plus their plan-reported scratch), per-profile
             row accumulators (128 maxima for Thin,1024 power sums and a window count for Detailed) and one latest immutable frame per profile in station state. No
             subscriber-specific FFT or unbounded queue. Process the two independent start schedules
             against this same forward-only SourceFile reader. Release common history before the
             minimum next needed start; read only when space remains and retain lookahead only for
             those windows. Pad outside EOS without increasing actual source positions/progress;
             no second source file/parser, whole-recording float array or additional sample backlog. Starting/replacing/cancelling clears both
             latest frames; publication checks the existing complete current job tuple. Browser keeps
             at most600 Detailed rows (120s, 614400 level bytes), or120 Thin rows (15360 level bytes),
             including explicit gap slots, and one pending repaint. These are application retention
             bounds, not total RSS promises.

             **Crisp canvas geometry.** Render every frequency/time cell using integer device-pixel
             edges with a DPR-sized backing bitmap, image smoothing disabled and pixelated CSS image
             rendering; no blur/filter or interpolation of measured values. The whole fixed[0,3000)Hz span always fits the plot width; frequency mapping is f/3000*W,
             0Hz at left and3000Hz at right. Resize/DPR/zoom changes geometry only, not frequency
             span, FFT dimensions or native data. No horizontal frequency scrolling or minimum1024
             pixel canvas width. Let B be1024 Detailed or128 Thin and W the integer backing width.
             When W>=B, bin k spans[floor(k*W/B),floor((k+1)*W/B)) device pixels. When W<B,
             assign every native bin k to column floor(k*W/B); that column displays the maximum
             original q of its assigned bins, exactly once each, with no interpolation, frequency
             resampling of the retained array or skipped zero-width cells. This display-only maximum
             projection preserves narrow strong signals; it cannot show1024 separate bins in fewer
             than1024 physical columns. The complete original native array remains unchanged.
             Readout names the projected column's native-bin range and its maximum, and separately
             identifies the nearest native bin to the pointer frequency (clamped, ties upward) or the
             exact keyboard-selected bin. Native keyboard stepping never edits/aggregates the data.
             Axis labels/controls stay reachable with no horizontal page or frequency plot overflow.
             A pointer/focusable readout exposes selected
             native bin index, center Hz, original q-120 dBFS and row source interval; keyboard Left/Right moves one
             bin and Up/Down one retained row, clamped to available data. Gaps report no measurement.

             **Waterfall space and Speed.** The canvas fills its entire allotted box. New
             observed rows enter at the top and advance older rows downward at a fixed source-time
             scale; accumulated history is never stretched to fill the canvas. The Speed slider is
             v=0.5..8 in0.5 steps, default2, with numeric output 10*v CSS pixels per source second and
             Slow/Fast ends. Set p=10*v CSSpx/s. Detailed advances 2*v CSSpx per full0.2s row;
             Thin advances10*v CSSpx per full1s row. This changes only local presentation, never
             source replay, decoder, network cadence, sample clock or retained values.
             Round finite speed input to the nearest half-step with floor(2*value+0.5)/2,
             then clamp to[0.5,8]; nonfinite/unparseable input leaves speed unchanged.

             Let C be the actual CSS waterfall height, H=round(C*DPR) its backing height (minimum1),
             and T the newest accepted row's end_frame/12000. A row with source interval[a,b)
             occupies downward integer device-pixel edges
             [floor((T-b)*p*H/C),floor((T-a)*p*H/C)), clipped to[0,H).
             Thus the latest row starts at0; each new accepted source interval shifts existing
             history by its source-time duration times p, independent of retained row count N.
             Older rows leave through the bottom without sticking, stretching, wrapping or repeating.
             A shortened final row uses its actual interval. Paint absent/unobserved history dark
             RGB(0,0,12), including the part below a short recording; it is not a measurement.
             Explicit missing sequence slots remain grey RGB(96,96,96), never noise or repeated data.
             Zero-height rows, if any after integer rounding, contribute to pixel floor((T-b)*p*H/C).
             When several rows contribute to one pixel, use their per-bin maximum and mark the group
             unknown grey if any contributor is a gap. Native arrays remain unchanged.

             The visible source-time capacity is C/p seconds, independent of N. Display this
             capacity and the actual observed source interval separately. Retain the existing
             bounded history so reducing speed can expose earlier observations; never fabricate
             measurements for time outside retained observations. Time advances only on accepted
             source rows. Completed, cancelled, disconnected or stalled input freezes its last
             history; resizing or local controls may repaint but do not advance time. Replay is
             explicit and resets its job/history normally, without automatic looping.

             Pointer selection uses the exact source intervals contributing to its integer pixel.
             For measured pixels, choose the newest contributing native row as initial selection;
             Up/Down steps one visible native row, clamped. The readout separates the selected
             native bin/row value and interval from the projected native-bin/time ranges and maximum.
             For a gap, report unknown; for an unobserved pixel, report no measurement, without
             clamping it to the oldest measured row. Left/Right still steps native frequency bins.
             Speed or geometry changes recompute visible rows/readouts without mutating native data.

                          Keep spectrum above the fixed0..3000Hz ruler and waterfall. #54: the spectrum line is shown
             only with the per-browser option Show spectrum line (default off); hidden, the waterfall
             takes its height. Shown, its vertical scale is [E,0] dBFS, so no level clips at the top.
             The default signal height is 330 CSS px (splitter), at most 560. Allocate the remaining plot
             budget after headings/rulers/legend approximately1:5 to spectrum:waterfall, using explicit
             zero flex bases and min-height0 so intrinsic canvas bitmap heights cannot feed back into
             layout. Each backing bitmap is round(its actual CSS box * DPR), minimum1, and each
             canvas fills its allotted box exactly after drag, resize and zoom. Plot areas therefore
             use approximately17%/83% of their combined height, subject only to integer rounding.
             Headers, rulers and controls remain reachable at the existing pane minima and360px.
             No horizontal page/frequency scrolling or changed frequency span.

             Frequency ruler retains major500Hz/minor100Hz ticks with positions f/3000*W. Time ruler
             labels T at the top and source time t every5s within the viewport,
             at y=floor((T-t)*p*H/C)/DPR, omitting negative source times and colliding labels less
             than16CSSpx apart. The time scale and native/projected readouts use this same mapping;
             labels do not imply observations in unmeasured areas. Label elapsed source seconds, never synthetic UTC/RF frequency/dBm.
             A run of Tx rows (#61 CL-061-05) takes one band of 4 CSSpx instead of its source time; every other row keeps p, and the mapping and labels of times beyond the band stay exact: T-t counts without the run's source time, plus the band.
             Profile changes still clear browser history/old-profile frames; existing bounded history,
             source identities and one pending repaint remain unchanged.

             **Display levels and palette.** The display is a local presentation of calibrated
             levels, independent of source samples, FFT/averaging, wire quantization, Thin bandwidth
             and future decoding (#54, CL-054-02). The waterfall corner holds labelled keyboard-operable
             Sensitivity (WSJT-X Zero), Range (WSJT-X Gain) and Speed range sliders, each with an
             adjacent numeric output, repainting on every input event; Settings > General > Display
             holds Flatten and Show spectrum line. DisplayLevels gives the values and the fixed
             mapping: there is no Black level input, no Auto black and no noise estimate, and a new
             source, job or display profile changes no level. Sensitivity and Range change
             waterfall colours only; the legend shows both effective ends in dBFS. Inputs are rounded
             with floor(value+0.5) and clamped; nonfinite values leave settings unchanged. Clipping
             affects presentation only; the native values remain available. Repaint all retained
             rows when presentation controls change; samples/wire data never change or restart.

             For an original quantized level q, t=clamp(((q-120)-E)/R,0,1). Map t to this project's
             own RGB anchors, interpolating each channel linearly between adjacent anchors and
             rounding with floor(channel+0.5): t=0:(0,0,12), .15:(0,0,80), .35:(0,80,220),
             .50:(0,220,240), .65:(30,230,80), .80:(255,235,0), .95:(255,40,0),1:(255,0,0).
             Saturated/above-range signal is exactly RGB(255,0,0), never white. Below-floor/no-signal
             is RGB(0,0,12); gaps are RGB(96,96,96) and appear only for a real gap (#54: rows the station did not send within its retained window, a source or job change, an unknown-loss source epoch of the same receive as one row between the kept rows (CL-061-01); one or two live Thin rows paced out between two sent rows are drawn with the next row, not as a gap; live Thin sends keep a fixed 2 s grid from the previous deadline, restarted at a send more than 1 s late, so sends stay at least 1 s apart). This continuous level-to-color
             mapping does not interpolate spatial bins/rows: each rendered cell has one exact RGB
             color, fully opaque. Spectrum trace is RGB(180,245,220). Ruler/grid/text overlays stay
             outside waterfall measured cell interiors. A narrow labeled color legend uses these exact same anchors, positions and linear RGB
             channel interpolation/rounding, ending in the same saturated red; it displays the
             effective waterfall range. Rainbow hue progression does not assert monotonic luminance. Flatten is the optional per-row passband equalisation of DisplayLevels; no palette editor, gain normalization over time or new framework.

             Conventional presentation references, consulted2026-10-25: [WSJT-X User Guide9.2/14.7](https://wsjt.sourceforge.io/wsjtx-main_en.html#_wide_graph) describes spectral averaging,
             bin visibility and display level controls; [FlexRadio SmartSDR User Guide, Waterfall](https://edge.flexradio.com/www/offload/20260423063240/SmartSDR-Software-User-Guide.pdf)
             describes noise-floor black level and display range. These inform the operator's visual
             expectation, not numerical conformance or copied assets/code. The exact formulas,
             geometry and original palette above are authoritative for this implementation. A real
             busy FT8 recording MUST show multiple recognizable narrow time-varying transmissions
             against a dark noise floor with distinguishable brighter signals, reviewed at desktop
             and360px alongside these reference images; analytical tones alone do not meet visual
             acceptance. Readout remains calibrated dBFS rather than implying receiver RF power. */
    }
    attribute def BrowserDisplayPreference {
        attribute effectiveOrigin : String;
        attribute profileUuid : String;
        attribute savedChoice : DisplayProfile[0..1];
        attribute effectiveChoice : DisplayProfile;
        attribute storageAvailable : Boolean;
        doc /* Browser-owned preference for one effective origin and validated saved-profile UUID.
             The browser storage boundary isolates origins; a versioned UUID key stores only
             off/thin/detail, never credentials, device identifiers, station settings or decoded traffic.
             Boot ID and revision do not alter identity. Environment-only/no-profile use is nonpersistent. */
    }
    action def RestoreDisplayChoice {
        in preference : BrowserDisplayPreference;
        out effectiveChoice : DisplayProfile;
        doc /* Use a valid saved choice if available. Otherwise Detailed on every origin,
             including remote HTTPS, using existing1024 native bins at2.9296875Hz. Invalid/missing values or
             unavailable storage use that normal default without disabling in-memory selection.
             Explicit choices survive reload/browser restart for this origin/profile only. */
    }
    action def SelectDisplayChoice {
        in explicitChoice : DisplayProfile;
        in preference : BrowserDisplayPreference;
        out updatedPreference : BrowserDisplayPreference;
        doc /* An explicit user selection changes effective and saved choice for this viewer only.
             If storage is unavailable, retain effective choice in memory without a persistence claim.
             Subscribe with existing off/thin/detail commands; do not change decoder/radio mode,
             source measurements, station settings or other viewers. Automatic server fallback changes
             effective choice only, never overwrites the explicit saved choice, and retains existing
             single Thin fallback/no retry loop. Detailed keeps fast-link/up-to10KiB/s notice and
             no32kbit/s promise; Thin retains all bandwidth limits. */
    }
    action def TransferDisplay {
        in 'frame' : SpectrumFrame[0..1];
        in detailedFrame : DetailedSpectrumFrame[0..1];
        in requestedProfile : DisplayProfile;
        doc /* **Opt-in WebSocket extension.** Keep `wstx.v1`, 1024-byte incoming request/frame/message
             limits; outbound Thin/control payloads remain <=1024 bytes, except receive.state (RadioIO). Set the outbound write
             buffer cap to4096 bytes to admit a <=2048-byte Detailed event while reserving a full
             1024-byte control payload and two conservative14-byte framing allowances. Preserve existing station.get/status/error envelopes, validation order,
             binary1003, heartbeats and liveness unchanged. Add exact three-field requests
             `{v:1,type:"recording.get"|"spectrum.thin"|"spectrum.detail"|"spectrum.off",id}`. `recording.get` returns
             `{v:1,type:"recording.state",id,data:{generation,source_id,job_id,state}}` with nullable
             IDs/state; full snapshot stays HTTP. A peer that has chosen a display subscription also
             receives the pushed event without id (WstxStationProtocol::PushedStationState, #10):
             `{v:1,type:"recording.state",data:{generation,source_id,job_id,state,import}}`, `import` null
             or `{id,state,received_bytes,total_bytes,error}` of the running import. It is sent once after
             the first subscription and then only on a change, checked once per second, on every display
             profile including Off; a change of received_bytes alone is sent at most once per
             5 s. It is an optional write that a full socket defers and never loses. The browser sends no
             recording.get: it reads GET /recording once per socket (the snapshot), after its own mutation
             and when the event differs from its snapshot in identity, job state or import identity;
             the rest of the import updates its view without a read. A failed read on a subscribed socket closes
             the socket: an event is sent once and no timer reads, so the reconnect reads again; an upload in progress then stops with its reservation left to cancel. Thin/detail/off acknowledge
             `{v:1,type:"spectrum.subscription",id,data:{profile:"thin"|"detail"|"off"}}`. Selected-profile
             absence returns recoverable `unavailable` for these commands. Every new connection starts
             off; legacy peers receive only existing status/heartbeat messages. New browser obtains
             status/profile/recording HTTP snapshots before opting into the selected profile and showing current
             recording data; unknown_command from an older server visibly disables recording display.
             Default browser selection is Detailed on every origin, including remote HTTPS,
             using existing1024 native bins at3000/1024 = 2.9296875Hz; no FFT/protocol/source
             resolution change. The selector offers
             "Detailed (fast link, up to 10 KiB/s per viewer)", "Thin (32 kbit/s link)" and Off.
             Without a valid saved choice, Detailed is selected. RestoreDisplayChoice resolves the
             origin/profile-specific BrowserDisplayPreference; explicit selector changes use
             SelectDisplayChoice. Only a user choice persists; runtime Thin fallback does not replace it.
             Storage failure/invalid value preserves normal defaults and usable in-memory controls.
             Detailed is explicitly selectable on HTTPS but carries no32 kbit/s promise. A server
             that supports recording/Thin but refuses spectrum.detail with unknown_command triggers
             one Thin subscription and visible "Detailed unavailable; using Thin" feedback. A server
             refusing recording.get/Thin disables recording display visibly as before. Never loop
             retries or replay a mutation. An environment-only server returns unavailable.
             No side effects occur through new WS requests apart from that connection's subscription.

             Only subscribed thin peers receive events
             `{v:1,type:"spectrum.frame",data:{boot_id,source_id,job_id,generation,sequence,first_frame,end_frame,levels}}`.
             IDs are UUIDs, sequence starts0 per replay row and increments even when rows are dropped;
             frame interval is [first_frame,end_frame), with first=12000*sequence, end=min(first+12000,
             source_frames). `levels` is exactly128 integers0..120 under 4.4's frequency/level contract.
             No null/unbounded extension fields. Each encoded event remains<=1024 bytes. No unsolicited
             recording snapshot/status payload change or application compression. Incoming binary still
             closes1003. Obsolete boot/source/job/generation events and callbacks from old sockets are
             ignored. Event loss cannot be used to infer missed decoder results.

             Detailed peers instead receive exactly
             `{v:1,type:"spectrum.detail.frame",data:{boot_id,source_id,job_id,generation,sequence,first_frame,end_frame,levels_b64}}`.
             A live row of a Tx period (#61 CL-061-04) carries "tx": true in data, in Thin and
             Detailed frames alike; the key is absent otherwise, and the browser paints such a
             row as a Tx row RGB(90,20,30), not with its levels; a run of such rows is collapsed to a thin band (CL-061-05).
             The UUID/safe-integer identity rules are unchanged, first=2400*sequence,
             end=min(first+2400,source_frames), sequence0..599. levels_b64 is canonical RFC4648
             standard base64 with padding: exactly1368 ASCII characters decoding to1024 bytes,
             each0..120. Reject wrong alphabet/padding/length/noncanonical pad bits, values>120,
             unknown/missing fields, unsafe/out-of-range sequence/interval or stale identity/socket;
             never render partially accepted data. Every encoded Detailed event is<=2048 UTF-8
             bytes; no binary messages, lossy nibble packing or application compression.
These application-payload and WebSocket exclusions do not prohibit the bounded
HTTP response content coding of12.1.1; no spectrum event is compressed by H1.

             One replaceable pending Thin event per peer and <=1 Thin send per second. #54 (CL-054-01):
             the station retains the last 25 Detailed rows (5 s) of the current job, and each
             Detailed peer receives every retained row after the last one it was sent, oldest
             first: 200 ms apart, 170 ms apart while rows wait (at most 5.9 sends per second,
             within 10 KiB/s), so a processing stall delays rows instead of dropping them; a peer
             further behind than the retained window has a real gap. A new subscription starts at
             the newest row; no replay of old
             frames after reconnect or off. Ready status replies and heartbeats take precedence;
             optional display output never waits in the connection loop and is skipped when send
             readiness/control headroom is unavailable. Its guard enforces event payload <=2048 and
             payload+1024+2*14<=4096; this intentionally replaces the previous996-byte guard, not
             bypasses it. A partially flushed optional write retains the original2s deadline;
             subsequent control output cannot reset or extend that deadline. Switching/off/reconnect
             forgets prior frame cursors and pending replacements; already buffered output remains
             bounded and is rejected by browser profile/identity guards. No old rows are replayed.
             Maintain existing two-second write deadline and bounded peer removal. Browser schedules
             at most one pending repaint and bounds history as in4.4. In normal operation two Thin
             clients stay within WstxStationProtocol::ThinLinkBudget, judged from the link byte log
             (#80); a recording replay or import carries no link budget. Browser sends one
             <=2048-byte chunk and waits for its response before the next. No completion-time
             promise is made for bulk import. Reconnection resets subscription and refreshes snapshots,
             never resumes or retries a mutation implicitly. */
    }
    action def PresentStation {
        attribute levels : DisplayLevels;
        doc /* **Crisp canvas geometry.** Render every frequency/time cell using integer device-pixel
             edges with a DPR-sized backing bitmap, image smoothing disabled and pixelated CSS image
             rendering; no blur/filter or interpolation of measured values. The whole fixed[0,3000)Hz span always fits the plot width; frequency mapping is f/3000*W,
             0Hz at left and3000Hz at right. Resize/DPR/zoom changes geometry only, not frequency
             span, FFT dimensions or native data. No horizontal frequency scrolling or minimum1024
             pixel canvas width. Let B be1024 Detailed or128 Thin and W the integer backing width.
             When W>=B, bin k spans[floor(k*W/B),floor((k+1)*W/B)) device pixels. When W<B,
             assign every native bin k to column floor(k*W/B); that column displays the maximum
             original q of its assigned bins, exactly once each, with no interpolation, frequency
             resampling of the retained array or skipped zero-width cells. This display-only maximum
             projection preserves narrow strong signals; it cannot show1024 separate bins in fewer
             than1024 physical columns. The complete original native array remains unchanged.
             Readout names the projected column's native-bin range and its maximum, and separately
             identifies the nearest native bin to the pointer frequency (clamped, ties upward) or the
             exact keyboard-selected bin. Native keyboard stepping never edits/aggregates the data.
             Axis labels/controls stay reachable with no horizontal page or frequency plot overflow.
             A pointer/focusable readout exposes selected
             native bin index, center Hz, original q-120 dBFS and row source interval; keyboard Left/Right moves one
             bin and Up/Down one retained row, clamped to available data. Gaps report no measurement.

             **Waterfall space and Speed.** The canvas fills its entire allotted box. New
             observed rows enter at the top and advance older rows downward at a fixed source-time
             scale; accumulated history is never stretched to fill the canvas. The Speed slider is
             v=0.5..8 in0.5 steps, default2, with numeric output 10*v CSS pixels per source second and
             Slow/Fast ends. Set p=10*v CSSpx/s. Detailed advances 2*v CSSpx per full0.2s row;
             Thin advances10*v CSSpx per full1s row. This changes only local presentation, never
             source replay, decoder, network cadence, sample clock or retained values.
             Round finite speed input to the nearest half-step with floor(2*value+0.5)/2,
             then clamp to[0.5,8]; nonfinite/unparseable input leaves speed unchanged.

             Let C be the actual CSS waterfall height, H=round(C*DPR) its backing height (minimum1),
             and T the newest accepted row's end_frame/12000. A row with source interval[a,b)
             occupies downward integer device-pixel edges
             [floor((T-b)*p*H/C),floor((T-a)*p*H/C)), clipped to[0,H).
             Thus the latest row starts at0; each new accepted source interval shifts existing
             history by its source-time duration times p, independent of retained row count N.
             Older rows leave through the bottom without sticking, stretching, wrapping or repeating.
             A shortened final row uses its actual interval. Paint absent/unobserved history dark
             RGB(0,0,12), including the part below a short recording; it is not a measurement.
             Explicit missing sequence slots remain grey RGB(96,96,96), never noise or repeated data.
             Zero-height rows, if any after integer rounding, contribute to pixel floor((T-b)*p*H/C).
             When several rows contribute to one pixel, use their per-bin maximum and mark the group
             unknown grey if any contributor is a gap. Native arrays remain unchanged.

             The visible source-time capacity is C/p seconds, independent of N. Display this
             capacity and the actual observed source interval separately. Retain the existing
             bounded history so reducing speed can expose earlier observations; never fabricate
             measurements for time outside retained observations. Time advances only on accepted
             source rows. Completed, cancelled, disconnected or stalled input freezes its last
             history; resizing or local controls may repaint but do not advance time. Replay is
             explicit and resets its job/history normally, without automatic looping.

             Pointer selection uses the exact source intervals contributing to its integer pixel.
             For measured pixels, choose the newest contributing native row as initial selection;
             Up/Down steps one visible native row, clamped. The readout separates the selected
             native bin/row value and interval from the projected native-bin/time ranges and maximum.
             For a gap, report unknown; for an unobserved pixel, report no measurement, without
             clamping it to the oldest measured row. Left/Right still steps native frequency bins.
             Speed or geometry changes recompute visible rows/readouts without mutating native data.

                          Keep spectrum above the fixed0..3000Hz ruler and waterfall. #54: the spectrum line is shown
             only with the per-browser option Show spectrum line (default off); hidden, the waterfall
             takes its height. Shown, its vertical scale is [E,0] dBFS, so no level clips at the top.
             The default signal height is 330 CSS px (splitter), at most 560. Allocate the remaining plot
             budget after headings/rulers/legend approximately1:5 to spectrum:waterfall, using explicit
             zero flex bases and min-height0 so intrinsic canvas bitmap heights cannot feed back into
             layout. Each backing bitmap is round(its actual CSS box * DPR), minimum1, and each
             canvas fills its allotted box exactly after drag, resize and zoom. Plot areas therefore
             use approximately17%/83% of their combined height, subject only to integer rounding.
             Headers, rulers and controls remain reachable at the existing pane minima and360px.
             No horizontal page/frequency scrolling or changed frequency span.

             Frequency ruler retains major500Hz/minor100Hz ticks with positions f/3000*W. Time ruler
             labels T at the top and source time t every5s within the viewport,
             at y=floor((T-t)*p*H/C)/DPR, omitting negative source times and colliding labels less
             than16CSSpx apart. The time scale and native/projected readouts use this same mapping;
             labels do not imply observations in unmeasured areas. Label elapsed source seconds, never synthetic UTC/RF frequency/dBm.
             A run of Tx rows (#61 CL-061-05) takes one band of 4 CSSpx instead of its source time; every other row keeps p, and the mapping and labels of times beyond the band stay exact: T-t counts without the run's source time, plus the band.
             Profile changes still clear browser history/old-profile frames; existing bounded history,
             source identities and one pending repaint remain unchanged.

             **Display levels and palette.** The display is a local presentation of calibrated
             levels, independent of source samples, FFT/averaging, wire quantization, Thin bandwidth
             and future decoding (#54, CL-054-02). The waterfall corner holds labelled keyboard-operable
             Sensitivity (WSJT-X Zero), Range (WSJT-X Gain) and Speed range sliders, each with an
             adjacent numeric output, repainting on every input event; Settings > General > Display
             holds Flatten and Show spectrum line. DisplayLevels gives the values and the fixed
             mapping: there is no Black level input, no Auto black and no noise estimate, and a new
             source, job or display profile changes no level. Sensitivity and Range change
             waterfall colours only; the legend shows both effective ends in dBFS. Inputs are rounded
             with floor(value+0.5) and clamped; nonfinite values leave settings unchanged. Clipping
             affects presentation only; the native values remain available. Repaint all retained
             rows when presentation controls change; samples/wire data never change or restart.

             For an original quantized level q, t=clamp(((q-120)-E)/R,0,1). Map t to this project's
             own RGB anchors, interpolating each channel linearly between adjacent anchors and
             rounding with floor(channel+0.5): t=0:(0,0,12), .15:(0,0,80), .35:(0,80,220),
             .50:(0,220,240), .65:(30,230,80), .80:(255,235,0), .95:(255,40,0),1:(255,0,0).
             Saturated/above-range signal is exactly RGB(255,0,0), never white. Below-floor/no-signal
             is RGB(0,0,12); gaps are RGB(96,96,96) and appear only for a real gap (#54: rows the station did not send within its retained window, a source or job change, an unknown-loss source epoch of the same receive as one row between the kept rows (CL-061-01); one or two live Thin rows paced out between two sent rows are drawn with the next row, not as a gap; live Thin sends keep a fixed 2 s grid from the previous deadline, restarted at a send more than 1 s late, so sends stay at least 1 s apart). This continuous level-to-color
             mapping does not interpolate spatial bins/rows: each rendered cell has one exact RGB
             color, fully opaque. Spectrum trace is RGB(180,245,220). Ruler/grid/text overlays stay
             outside waterfall measured cell interiors. A narrow labeled color legend uses these exact same anchors, positions and linear RGB
             channel interpolation/rounding, ending in the same saturated red; it displays the
             effective waterfall range. Rainbow hue progression does not assert monotonic luminance. Flatten is the optional per-row passband equalisation of DisplayLevels; no palette editor, gain normalization over time or new framework.

             Conventional presentation references, consulted2026-10-25: [WSJT-X User Guide9.2/14.7](https://wsjt.sourceforge.io/wsjtx-main_en.html#_wide_graph) describes spectral averaging,
             bin visibility and display level controls; [FlexRadio SmartSDR User Guide, Waterfall](https://edge.flexradio.com/www/offload/20260423063240/SmartSDR-Software-User-Guide.pdf)
             describes noise-floor black level and display range. These inform the operator's visual
             expectation, not numerical conformance or copied assets/code. The exact formulas,
             geometry and original palette above are authoritative for this implementation. A real
             busy FT8 recording MUST show multiple recognizable narrow time-varying transmissions
             against a dark noise floor with distinguishable brighter signals, reviewed at desktop
             and360px alongside these reference images; analytical tones alone do not meet visual
             acceptance. Readout remains calibrated dBFS rather than implying receiver RF power.

             **Integrated UI.** One browser window/page per station. Spectrum and waterfall
             occupy the upper pane; profile/status/import/replay/controls and future decoded messages
             occupy the lower pane. No placeholder decoded messages or signal data. Horizontal
             separator is focusable with `role=separator`, horizontal orientation, accessible name,
             current/min/max pane sizes and visible focus. Pointer/mouse/touch drag changes upper
             height; Up/Down change it by 16 px, Home/End select min/max. Minimum upper/lower pane
             heights are 160/200 CSS px excluding a 12 px separator. If available height is smaller,
             scroll the page rather than violate minima. Lower controls also scroll independently
             when needed. Initial split is 50% of available height clamped to minima. Recompute/clamp
             on viewport changes; no server persistence of pane size. Verify 1100x850 and 360x640,
             keyboard-only use, touch input, 200% zoom and literal rendering of source/status text.
             No horizontal page overflow; axis labels and primary controls remain reachable. */
    }
    state def ReceiveLifecycle {
        attribute cancelAccepted : Boolean;
        attribute workerReleased : Boolean;
        attribute sourceComplete : Boolean;
        attribute processingFailed : Boolean;
        entry; then running;
        state running; state cancelling; state completed; state cancelled; state failed;
        transition cancel first running if cancelAccepted then cancelling;
        transition release first cancelling if workerReleased then cancelled;
        transition complete first running if sourceComplete and workerReleased and not processingFailed and not cancelAccepted then completed;
        transition fail first running if processingFailed and workerReleased and not cancelAccepted then failed;
        doc /* contract 4.4: accepted cancellation already changes running to cancelling;
             otherwise processing failure prevents completion even with simultaneous EOS.
             While a failed worker is held, state remains nonterminal. Guards are disjoint;
             every terminal receive transition requires worker release. */
    }
    enum def ImportBrowserEvent {
        enum start; enum accepted; enum reservation_rejected; enum abort; enum response_lost;
        enum reconciled; enum terminal;
    }
    state def BrowserImportLifecycle {
        attribute acceptedEvent : ImportBrowserEvent;
        entry; then idle;
        state idle; state pending; state pendingCancel; state cleanupRequested; state uploading; state reconciling;
        transition begin first idle if acceptedEvent == ImportBrowserEvent::start then pending;
        transition reserved first pending if acceptedEvent == ImportBrowserEvent::accepted then uploading;
        transition cancelPending first pending if acceptedEvent == ImportBrowserEvent::abort then pendingCancel;
        transition cancelAcceptedReservation first pendingCancel if acceptedEvent == ImportBrowserEvent::accepted then cleanupRequested;
        transition cancelledReservationRejected first pendingCancel if acceptedEvent == ImportBrowserEvent::reservation_rejected then idle;
        transition cancelledReservationUnknown first pendingCancel if acceptedEvent == ImportBrowserEvent::response_lost then reconciling;
        transition cleanupObserved first cleanupRequested if acceptedEvent == ImportBrowserEvent::terminal then reconciling;
        transition cleanupUnknown first cleanupRequested if acceptedEvent == ImportBrowserEvent::response_lost then reconciling;
        transition reservationRejected first pending if acceptedEvent == ImportBrowserEvent::reservation_rejected then idle;
        transition reservationUnknown first pending if acceptedEvent == ImportBrowserEvent::response_lost then reconciling;
        transition abortUpload first uploading if acceptedEvent == ImportBrowserEvent::abort then reconciling;
        transition uploadUnknown first uploading if acceptedEvent == ImportBrowserEvent::response_lost then reconciling;
        transition observed first reconciling if acceptedEvent == ImportBrowserEvent::reconciled then idle;
        transition finished first uploading if acceptedEvent == ImportBrowserEvent::terminal then idle;
        doc /* contract 12.6: pendingCancel retains local cancellation intent while awaiting
             the reservation response. It never starts PUT. An accepted response gives
             the exact import ID: cleanupRequested sends DELETE for that returned ID,
             with zero PUT requests, then reconciles GET. Rejected responses end pending
             cancellation without PUT/DELETE. Lost reservation/cleanup responses enter
             reconciling; no cancellation success or cleanup is inferred. An unknown
             reservation ID is observed through GET, never guessed or automatically retried.
             UI abort during upload stops PUT and sends DELETE independently, then uses GET
             to reconcile uncertain outcome. A lost reservation response is reconciled from
             GET /recording, which exposes any accepted import ID. Never retry a mutation,
             resume upload, replay, or infer rollback from a missing response. reconciling
             persists on unavailable transport; no fabricated successful snapshot.
             A known reservation rejection ends local pending, visibly reports the returned
             error and starts no PUT/DELETE/retry; authoritative busy/degraded/identity state
             remains unchanged until an independently validated snapshot changes it.
             idle means no local upload, not permission to ignore authoritative busy state. */
    }
    action cancelImport : CancelImport;
    action replaySpectrum : ReplaySpectrum;
    action cancelReceive : CancelReceive;
    action spectrum : CalculateSpectrum;
    action transfer : TransferDisplay;
    action present : PresentStation;
    satisfy WstxRequirements::'CL-006-02' by replaySpectrum;
    satisfy WstxRequirements::'CL-006-03' by spectrum;
    satisfy WstxRequirements::'CL-006-04' by cancelReceive;
    dependency importAuthority from cancelImport to WstxArchitecture::physicalStation::backend::stations::station;
    dependency receiveOwner from replaySpectrum to WstxArchitecture::physicalStation::backend::stations::receive;
    dependency cancellationOwner from cancelReceive to WstxArchitecture::physicalStation::backend::stations::receive;
    dependency spectrumOwner from spectrum to WstxArchitecture::physicalStation::backend::stations::receive;
    dependency transferOwner from transfer to WstxArchitecture::physicalStation::backend::stations::web;
    dependency browserOwner from present to WstxArchitecture::physicalStation::frontend::browsers;
    dependency sharedInput from SampleBlock to WstxArchitecture::physicalStation::backend::stations::audio;
    item def DecodeJob :> WstxRecordingReceive::ReceiveJob {
        attribute :>> kind = WstxRecordingReceive::ReceiveKind::live;
        attribute settings : Settings;
        attribute available_count : Integer;
        attribute search_limited : Boolean;
        assert constraint boundedProgress {
            processed_frames >= 0 and processed_frames <= (900719925 * 10000000 + 4740991) and
            available_count >= 0 and available_count <= 2048
        }
        doc /* Existing station receive-job authority, kind=live with immutable mode.
             One import OR recorded spectrum OR continuous receive; no queue.
             Source-relative FT8/FT4 windows, reliable live ring and epoch rules12.8.
             Numerical recorded fixtures have no production receive operation. */
    }
    item def LiveTimedResultRecord :> ResultRecord {
        attribute period_start_utc : String[0..1];
        attribute dt_seconds : Real[0..1];
        doc /* Live-only manager extension4.7.4/12.8, native Decode unchanged.
             Both null without correlated source timing; otherwise nearest nominal
             period and signed relative seconds via WstxRadioIO::RelativeDecodeTiming.
             Existing2048-byte live record cap and stricter1024-byte modem cap remain. */
    }
    item def ResultPage {
        attribute v : Integer = 1;
        attribute correlation : WstxRecordingReceive::Correlation;
        attribute mode : Mode;
        attribute 'state' : WstxRecordingReceive::ReceiveState;
        attribute error : WstxRecordingReceive::ErrorCode[0..1];
        attribute search_limited : Boolean;
        attribute first_sequence : Integer;
        attribute next_sequence : Integer;
        attribute available_count : Integer;
        attribute 'next' : Integer;
        attribute more : Boolean;
        item records : LiveTimedResultRecord[0..16];
        attribute latest_decode : WstxRadioIO::LatestDecodePeriod[0..1];
        assert constraint pageCursor { first_sequence >= 0 and next_sequence >= first_sequence and next_sequence <= (900719925 * 10000000 + 4740991) and available_count == next_sequence - first_sequence and available_count <= 2048 and 'next' >= first_sequence and 'next' <= next_sequence }
        doc /* Exact12.8 live envelope<=16384bytes,record<=2048bytes; Thinlimit1/page3072.
             Each record sequence<next_sequence,start_frame<actually captured next_frame.
             cursor<first=>410cursor_expired,cursor>next=>400,cursor==next=>empty.
             No file decode operation/snapshot/page endpoint. */
    }
    action def AdmitDecode {
        in source : WstxRecordingReceive::SourceDescriptor[0..1];
        in settings : Settings;
        out job : DecodeJob;
        doc /* Production12.8 live start only; selected-profile auth/Origin/schema,
             boot/generation/profile-revision and shared receive admission precede capture.
             Mode immutable. Source absent during opening before first provider ACK;
             no publication until acknowledged full tuple. Initialstart freshjob/gen,
             firstsourceACK samejob/gen;
             subsequent unknownepoch freshsource/job/gen beforeproviderACK and ring reset.
             Recorded waveforms are internal numerical/integration fixtures, no file API. */
    }
    action def LiveWindowSchedule {
        doc /* Live window schedule (#47, CL-007-05): with a correlated source UTC anchor the
             shared receive owner completes two windows per period at fixed source-counter
             residues of the advance: FT8 prompt +13.8 s/15 s of audio (DT -1.7..+0.66 s)
             and late +15.7 s/15 s (DT +0.2..+2.56 s); FT4 prompt +6.5 s/7.5 s (DT
             -1.5..+0.96 s) and late +7.9 s/7.5 s (DT -0.1..+2.36 s). Overlapping frames are
             deduplicated by the modem history. The late window arriving during the prompt
             decode waits in one slot until that decode completes; any other window arriving
             during a decode abandons it as an overrun (last_overrun names the newest skipped
             support). The residues come from the epoch's UTC anchor plus the measured
             capture-clock offset (CL-007-05): when it moved by more than 50 ms the residues
             are recomputed and each scheduled window's next completion moves by the signed
             correction of any size, staying the completion of the same UTC period (no
             wrap by a period). One moved into the past completes now; coinciding ones
             complete one after the other in schedule order (prompt, then late); each then
             returns to its grid, so none is dropped or repeated. A scheduled late window
             extends its period's view under the same id.
             Without a correlated anchor the counter grid (30 s/15 s, 15 s/7.5 s) applies. */
    }
    action def PublishResults {
        in job : DecodeJob;
        in records : ResultRecord[0..2048];
        out page : ResultPage;
        doc /* Stationauthority rechecks fullidentity/generation beforeappend. Cancelinvalid
             beforeack; terminalonlyafterrelease<=250ms; retain marked partials onstop/failure.
             Newjob/source/restart invalidates oldpages/callbacks. Reliable2048/2MiB live ring;
             evictionadvancesfirst_sequence, lifetime safecountersneverreset within an epoch.
             SearchLimited=>failed/decode_limit+search_limited=true,acceptedpartialsretained;
             accepted cancellation has priority. No invented calls/exception strings.
             Browser onependingpage,Thinlimit1/starts>=4sbehindexplicitstatus; optional
             spectrum<=1/2s; two32kbitclients<=3000accountedB/s/direction,status<=2s.
             No automaticmutationreplay or browsermodem/clockauthority. */
    }
    action admitDecode : AdmitDecode;
    action liveWindowSchedule : LiveWindowSchedule;
    action publishResults : PublishResults;
    satisfy WstxRequirements::'CL-007-01' by admitDecode;
    satisfy WstxRequirements::'CL-007-02' by publishResults;
    satisfy WstxRequirements::'CL-007-05' by liveWindowSchedule;
    dependency admissionOwner from admitDecode to WstxArchitecture::physicalStation::backend::stations::receive;
    dependency publicationOwner from publishResults to WstxArchitecture::physicalStation::backend::stations::web;
    dependency viewerOwner from publishResults to WstxArchitecture::physicalStation::frontend::browsers;

    package IndependentVerification {
        doc /* All cases cost 2 - isolated automated tests on Windows development PC.
             Actual candidate server/browser, disposable profiles, synthetic byte fixtures,
             independent direct DFT and pinned actual recordings with chapter13 provenance.
             No radio/audio device/live station. Definitions and candidate source presence are not acceptance results.
             Independent case expectations are retained in WstxRequirements and this package; production/library output is not their oracle. */
        verification receiveIsolation {
            subject operation : CancelReceive;
            objective { verify WstxRequirements::'CL-006-02'; verify WstxRequirements::'CL-006-04'; }
            doc /* TC-018-003: setup/input/action: Two independent authenticated clients race import/replay/cancel using current/stale/wrong boot, profile, generation and token IDs; inject a late worker publication, disconnect/reconnect, restart during replay; separately restart during an uncommitted reserved/receiving import, then query the fresh snapshot and old import/job IDs before starting new work; run maximum source and four processes. In a separate current running job with no cancellation, hold worker release, report processing failure, then source completion, inspect state before release and finally release the worker. Enumerate every 12.6 endpoint with missing/wrong Origin/cookie, method, media type, body/schema and token errors. In a real browser, reject the reservation POST with known409 busy and separately503 storage_unavailable; observe local pending/error display and all subsequent requests.
                 Independent expected oracle: Exactly one serialized start wins. A known rejected reservation ends local pending and visibly reports its exact error, sends no PUT/DELETE/retried POST and preserves authoritative busy/degraded/identity state; it cannot fabricate an accepted import or successful snapshot. Restart preserves the last committed source UUID/bytes but changes boot, resets generation0 and returns import:null/job:null; prior import resource and job DELETE return404, with no cancelled-job record or automatic replay. Errors and snapshots match fixed state-transition table, lost-response recovery never auto-replays. Wrong identities cannot affect selected station. Replay cancel invalidates output before ack and reaches terminal/worker release <=250 ms under stated workload; import cancel prevents commit when accepted before committing, acknowledges locally<=250ms, cleans normally<=1s or becomes failed/storage_unavailable by5s with slot/files quarantined and no false deletion; progress never exceeds frame count. The held-worker failure vector stays running/nonterminal before release, becomes failed on release and is never completed, including simultaneous source completion. Instrument retained block/worker/slot counts against contract bounds; this is not a total RSS claim. Original station.get/auth/profile regression assertions remain in force. Also corrupt the committed original/metadata/manifest in separate fixtures, restart, open a fresh browser, obtain200 snapshot with source_error and valid identities, then import a valid replacement using those identities: replacement succeeds, clears source_error and replays; replay before replacement returns409 recording_unavailable. */
        }
        dependency tracereceiveIsolation from receiveIsolation to WstxRequirements::'TC-018-003';
        verification calibratedDisplay {
            subject operation : CalculateSpectrum;
            objective { verify WstxRequirements::'CL-006-03'; }
            doc /* TC-010-001: setup/input/action: Independently synthesize silence, DC, coherent tones at 750/1500/2250 Hz at amplitudes 0.5/0.25, two simultaneous tones, a noncoherent tone, clipped input and a burst with specified source-frame start/end. Compute selected windows using a direct DFT test oracle; replay through real browser.
                 Independent expected oracle: Direct DFT uses published formula without candidate FFT/provider helpers; peak group equals floor(k/4) for coherent bins and row interval follows window-start rule. Half-amplitude change is -6.0206 dB within 0.05 dB prequantization; quantized levels add <=0.5 dB. Silence equals floor; DC uses one-sided exception. Require normal and portable scalar FFT paths against the same direct DFT oracle, then compare full selected rows, axes/legend/row gaps in DOM/canvas sampling and source metadata, not screenshot resemblance alone. */
        }
        dependency tracecalibratedDisplay from calibratedDisplay to WstxRequirements::'TC-010-001';
        verification boundedThinLink {
            subject operation : TransferDisplay;
            objective { verify WstxRequirements::'CL-006-03'; verify WstxRequirements::'CL-006-04'; }
            doc /* TC-010-002: defined in WstxRequirements::'TC-010-002'. */
        }
        dependency traceboundedThinLink from boundedThinLink to WstxRequirements::'TC-010-002';
        verification integratedPanes {
            subject operation : PresentStation;
            objective { verify WstxRequirements::'CL-006-03'; }
            doc /* TC-010-003: setup/input/action: Real browser at 1100x850 and 360x640: import actual recording, verify one station page, drag divider beyond both extremes, use keyboard/touch/zoom and resize during replay. Repeat four independent station windows.
                 Independent expected oracle: Measured pane bounds meet 160/200 px minima, separator is 12 px and accessible, keyboard steps16px/Home/End clamp, small-height page scrolls, no horizontal page overflow, controls and axes remain reachable. Pointer/keyboard actions change only that station's pane, no second waterfall window appears and data/source identity survives resize. Browser assertions plus desktop/narrow screenshots verify actual layout. */
        }
        dependency traceintegratedPanes from integratedPanes to WstxRequirements::'TC-010-003';
        verification nativeBinDetail {
            subject operation : CalculateSpectrum;
            objective { verify WstxRequirements::'CL-006-03'; verify WstxRequirements::'CL-006-04'; }
            doc /* TC-010-004: Executable companions: server/src/recording_tests.rs, server/src/protocol_tests.rs and tests/recording.test.cjs; cost2 automated Windows offline.
                 Setup/actions: Cost2, automated Windows Rust numerical tests and real browser/server fixtures. Synthesize independent PCM16 vectors: silence/DC, single tones at native k256 and k257 separately and summed with fixed phases/amplitudes; simultaneous750 and756.25 Hz tones; amplitude0.5/0.25 and bursts at source frames1920/2400/2880 and sources of1/2399/2400/2401/2879/2880/2881 frames with short/EOS windows. Compare N4096 normal/scalar FFT bins and complete selected power-averaged rows against a test-only f64 direct DFT of the hand-specified periodic Hann formula, without candidate FFT/window/quantizer helpers. Replay one source with simultaneous Thin and Detailed peers, then race cancellation/replacement.
                 Independent expected oracle: Native k256=750Hz and k257=752.9296875Hz remain separate values; Hann leakage/interference is compared to the independent DFT, not an assertion that adjacent equal tones must form two local maxima. 750/756.25Hz signal retains independently predicted bin peaks/valley; no four-bin pooling or frequency resampling. Prequantized error <=0.05dB on independently specified bins above -80dBFS and absolute amplitude error<=2e-6 elsewhere; quantized values differ by <=1 level from independently rounded DFT, exact silence0. One coherent half-amplitude tone gives -6.0206dBFS before PCM error. Row assignment uses global hop480: five starts/full2400-frame row, one to five at EOS, including start2400 in source_frames2401. Independent mean-square amplitude then10log10 differs from Thin maximum and from averaging dB; zero Hann endpoint yields legitimate final silence for2401. Intervals are2400 frames, shortened EOS, sequence<=599. One source/worker, the latest Thin frame and the retained Detailed rows (#54, at most 25), declared workspace/history limits and cancellation release<=250ms remain; stale publications cannot overwrite either profile. Thin numerical expectations from TC-010-001 remain unchanged. */
        }
        dependency tracenativeBinDetail from nativeBinDetail to WstxRequirements::'TC-010-004';
        verification crispDetailTransport {
            subject operation : PresentStation;
            objective { verify WstxRequirements::'CL-006-03'; verify WstxRequirements::'CL-006-04'; }
            doc /* TC-010-005: Executable companions: server/src/recording_tests.rs, server/src/protocol_tests.rs and tests/recording.test.cjs; cost2 automated Windows offline.
                 Setup/actions: Cost2, automated Windows real browser/candidate server plus deterministic injected wire fixtures. Exercise cleartext loopback and HTTPS defaults; explicit three-profile changes, old Thin-only/older server, simultaneous Thin/Detailed peers, malformed base64 alphabet/padding/pad bits/decoded lengths/values, unknown/missing keys, safe-integer/interval edges, wrong tuples/old sockets and skipped sequences. Use alternating known quantized levels in adjacent native bins/rows and read actual getImageData at1100x850 and360x640, DPR1/2,200% zoom, splitter extremes, resize and repaint; exercise the fixed level mapping (#54 DisplayLevels: reference, Zero/Gain sliders, no automatic level) and range/legend/readout consistency. Retain actual busy FT8 recording desktop/mobile screenshots and compare their trace/noise contrast, orientation and rulers qualitatively with WSJT-X/FlexRadio reference images. Stall Detailed output with a controlled sink returning Pending, then issue status/control and cancel/off.
                 Independent expected oracle: Detail events have exact schema,1024 decoded bytes, canonical1368-char base64 and<=2048 UTF-8 bytes; exactly-at-limit values accepted and malformed/obsolete input leaves canvas/history unchanged. At most 1 Hz Thin and, for Detailed, 5 rows/s steady with catch-up of retained rows at most 5.9 rows/s (#54 TransferDisplay); no second worker. Thin/control input1024 and binary1003 guards preserved. Optional write test independently requires readiness/control priority,4096 cap,1024+28 control reserve; Detailed fast-link status responses display<=2s on unshaped localhost with two peers. The 32 kbit/s Thin/Off budget is judged from the link byte log (#80, TC-080-001). Every origin defaults Detailed; explicit saved Thin/Off is honored and fallback attempts Thin once and labels unavailability. Explicit Detailed/Thin/Off survives reload and reopened browser context; origin/port/profile UUIDs isolate choices while boot/revision changes preserve them. Invalid/denied storage uses defaults without page errors or disabling memory selection. Only versioned UUID keys and enumerated values are stored, no secrets/traffic. Automatic fallback preserves saved Detailed; explicit Thin replaces it. Existing wire tests remain unchanged, with no synthesized decoded records. Pixel oracle computes integer edges/fixed source-time cell edges from contract, samples interiors and both sides of boundaries for exact palette colors/uniform cells, using independently calculated RGB interpolation/rounding from the stated anchors, with grey gaps and dark unobserved areas on a full-height canvas; no blended spatial colors. New rows enter at top; Auto ignores median0 then locks once at median-3dB, manual Black/Range disables it, job/profile reset restores30dB/Auto and original calibrated data remains invariant. Frequency500/100Hz ticks and visible source-time5s ruler agree with pixel/readout positions and clipping. Fixed0..3000Hz axis endpoints/ticks through resize/DPR/zoom, no horizontal frequency scroll, unmodified native1024-value buffer, peak-preserving max projection with every bin contributing at widths below1024, native/projected readout centers/ranges/levels/intervals, keyboard selection, recent-row orientation,600-row cap and no page overflow hold through geometry changes. Thin uses the same integer geometry with128 bins; original numerical/wire values stay unchanged. A narrow strong tone at every native-bin position contributes to its assigned column and never disappears when W<B. Screenshots establish actual layout and independently synthesized data establishes numerical correctness. */
        }
        dependency tracecrispDetailTransport from crispDetailTransport to WstxRequirements::'TC-010-005';
        verification fullHeightSliderPresentation {
            subject operation : PresentStation;
            objective { verify WstxRequirements::'CL-006-03'; verify WstxRequirements::'CL-006-04'; }
            doc /* TC-010-006: implemented executable companion in tests/recording.test.cjs.
                 Setup/actions: Cost2 automated Windows real browser/candidate fixtures. Inject independently known native rows of2,75,600 Detailed or120 Thin values with contrasting bins/rows and gaps; inspect actual RGBA/backing and CSS box dimensions at desktop1100x850/mobile360x640, DPR1/2,200% zoom and splitter bounds. Exercise Sensitivity-30/0/+30 and Speed1/2/8 via input, keyboard and numeric outputs, Range 10/50/80 (#54), new jobs/profiles and resize. Replay actual busy FT8 with a red saturated carrier, capture desktop/mobile screenshots and move both live sliders.
                 Independent expected oracle: Independent oracle: palette endpoint/saturated cells are exactly[255,0,0,255], floor/no-signal[0,0,12,255], no white signal cells; legend uses identical RGB anchors/endpoints. With the fixed reference B=-85 and R=50 (#54), g=+10 yields E=-95 and g=-30 yields E=-55, clamped[-120,-R]; original row arrays, source/job/generation and curve base scale stay unchanged. No setting follows the signal or resets on a new job or profile; Sensitivity, Range and Speed persist per browser. Fixed source-time scrolling, independent pixel movement, clipping, gap and unobserved-region oracles are specified in TC-010-007. Native/projected readouts and rulers agree with that mapping. Spectrum/waterfall CSS heights follow1:5 within2CSSpx rounding, actual bitmap sizes equal rounded CSS boxes times DPR, neither geometry nor intrinsic height drifts over repeated paints. No horizontal overflow/changed0..3000Hz span, interpolation, fake history or network/source-rate change. Real FT8 screenshots show a full-height waterfall canvas with unobserved regions dark, dark floor, red strongest traces and visible working live sliders; original numeric/wire/security assertions remain. */
        }
        dependency traceFullHeightSliders from fullHeightSliderPresentation to WstxRequirements::'TC-010-006';
        verification sourceTimeScroll {
            subject operation : PresentStation;
            objective { verify WstxRequirements::'CL-006-03'; verify WstxRequirements::'CL-006-04'; }
            doc /* TC-010-007: implemented executable companion in tests/recording.test.cjs.
                 Setup/actions: Cost2 automated on the Windows development PC with real Chromium/candidate server and independently injected accepted source rows. Start empty; inject a uniquely marked row then successive Detailed0.2s rows and Thin1s rows, at Speed0.5/1/2/8. Inspect actual RGBA before/after each update, through enough source time to move the mark off the bottom. Exercise short/EOS rows, gaps, no input/completion/cancel/disconnect, invalid/stale frames, new replay/profile, resize, DPR1/2,200% zoom and minimum splitter height at360CSSpx, desktop and2048px width.
                 Independent expected oracle: With p=10*v and newest end T, independently calculate each row edges floor((T-b)*p*H/C)..floor((T-a)*p*H/C); a fixed mark advances by2*v CSSpx per Detailed update or10*v per Thin update, independent of N. Minimum speed0.5 gives5CSSpx/s, half Speed1; default2 gives20CSSpx/s. It exits below H and never sticks or repeats. Empty/unobserved pixels are exactly navy with no-measurement readout; explicit gaps grey. Changing height changes capacity C/p, not pixels per source second; changing speed changes displacement without modifying tuples/data/network. Short EOS uses actual duration; no source row means no motion; stale/invalid frames cannot move history. Pointer native/projected intervals, keyboard clamps and5s rulers match the same time mapping. Existing sliders remain visible and keyboard-operable; actual canvas remains full allotted height, spectrum:waterfall1:5 and fixed0..3000Hz. Existing palette/sensitivity and wire/numerical assertions remain unchanged. */
        }
        dependency traceSourceTimeScroll from sourceTimeScroll to WstxRequirements::'TC-010-007';
    }
    doc /* Implementation freedoms: Rust file layout; existing-library/std storage
         commit primitives preserving the declared commit point; small bounded parser
         mechanics; test-only fault injection; canvas drawing mechanisms preserving the exact
         authoritative RGB palette and prescribed integer geometry. No implicit changes
         to wire/schema/state/units/bounds/authority/errors/oracles, extra dependencies,
         speculative FFT wrapper, device capabilities or transmit lifecycle. */
    doc /* contract 4.7.5/12.8.1 coordinated operating selection is modeled by
         WstxOperatingReceive. This companion retains the unchanged legacy strict
         receive/radio/result shapes and owner/cancellation/source contracts.
         New selection uses the same authority, explicit actual release before
         setters/new capture and a fresh context, not a second pipeline or actor. */

    doc /* Issue22 target health contract CL-022-05: browser/session authorization,
         CAT connection/readback and audio/decoder are separate lifecycles. HTTP401
         invalidates session readiness and affected current data within2seconds even
         if the old WS is open; retained-key proof can restore authorization without
         replaying mutations. Actual CAT identity/query provenance alone confirms radio
         frequency. Waiting/retry/quarantine marks retained radio facts unconfirmed;
         source/job/generation fences continue to govern latest decoded rows. Automatic
         CAT recovery never starts audio/decoder, clears unknown-operation barriers,
         replays user commands or keys PTT. Existing shared issue10 continuity helpers
         are reused. Authentication/challenge/recovery/status traffic is not part of a
         32 kbit/s link test; its bytes appear in the link byte log (#80). TC-022-008/009/010 own the
         independent target regression/native/live evidence. Actual dated freeze cause
         remains unproved until reproduced; this contract is not a diagnosis. */

}
