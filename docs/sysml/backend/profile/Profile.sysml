package WstxProfiles {
    private import ScalarValues::*;
    private import WstxRequirements::ImplementationState;
    private import WstxRequirements::AutomationState;
    private import WstxRequirements::'FR-001';
    private import WstxRequirements::'FR-016';
    private import WstxRequirements::'FR-021';
    private import WstxRequirements::'FR-022';
    private import WstxRequirements::'FR-023';
    private import WstxStationProtocol::'CL-005-03';
    private import WstxStationProtocol::'TC-022-004';
    private import WstxStationLink::RuntimeInputs;
    private import ModelBindings::Status;
    private import ModelBindings::Automation;
    private import ModelBindings::ImplementedIn;
    private import ModelBindings::TestedBy;
    private import ModelNotes::FollowsSource;
    private import ModelNotes::Conflict;
    private import WstxRequirements::'FR-019';
    private import WstxRequirements::'FR-002';
    private import WstxRequirements::'FR-009';
    private import WstxLiveReceive::'CL-008-02';
    private import WstxRecordingReceive::'CL-008-03';
    private import WstxRadioIO::'CL-008-04';
    private import WstxRadioIO::'CL-008-06';
    private import WstxRecordingReceive::'CL-006-04';
    private import WstxRadioSetup::'TC-044-002';
    private import WstxRadioSetup::'TC-044-004';
    private import WstxProfileAccess::NativeProfileDocument;
    private import WstxProfileAccess::HttpOutcome;
    private import WstxProfileAccess::maxRevision;
    private import WstxProfileAccess::ProfileDocument;
    private import WstxProfileAccess::SaveProfile;
    private import WstxProfileAccess::HttpProfilePut;
    private import WstxProfileAccess::ProfileAccess;
    private import WstxAudioStreams::ReceiveSamples;
    private import WstxProfileRecordings::RecordedSource;
    private import WstxRecordingTransfer::RecordingTransfer;
    doc /* The profile part (WstxProfiles::PersistedProfile, deployed as
         WstxArchitecture::StationProcess::profile): the saved profile of one station, its
         creation, its launch with ownership, its save through GET and PUT /profile, its stop
         and its recovery. Its directory is the outside thing
         WstxContext::OutsideThing::profileFiles. The recordings function of the part is
         WstxProfileRecordings; authentication is the web part's (WstxStationProtocol), the
         profile form the browser's (WstxOperatingLayout). */
    doc /* The content coding of a GET /profile body is
         WstxHttpContentCoding::HttpContentCodingBoundary's; the checks of this package come
         before it, and it adds no owner, wire JSON or WebSocket codec. */
    @ImplementedIn { module = "server/src/profile.rs; server/src/main.rs"; }
    enum def StartupOutcome {
        doc /* The outcome of a launch or a creation, written as the process output and the
             exit: ready and created end with exit 0, every other member with a nonzero
             exit. */
        enum ready; enum created; enum invalid_runtime_configuration;
        enum resource_unavailable; enum invalid_profile; enum unsupported_schema;
        enum unsupported_connection_type; enum profile_in_use; enum endpoint_in_use;
    }
    attribute profileFileMaxBytes : Integer = 16384 {
        doc /* The largest profile.json, in UTF-8 bytes. */
    }
    attribute profileHttpMaxBytes : Integer = 8192 {
        doc /* The largest PUT /profile body and the largest GET or PUT /profile response, in
             UTF-8 bytes. */
    }
    attribute readinessDeadlineSeconds : Integer = 10 {
        doc /* A launch reports readiness or exits within this time. */
    }
    dependency nativePersistence from NativeProfileDocument to 'FR-023';

    calc def PutDecision {
        doc /* The checks of a PUT in this order. authValid holds for trusted plaintext loopback
             or for exactly one expected cookie whose UUID and token verify. settingsValid
             judges the whole Settings object against every domain above; there is no partial
             edit. A transport body limit may answer 413 before this order. Every outcome
             but ok keeps the saved bytes, the revision and the settings. */
        @FollowsSource {
            reference = "RFC 6454 section 7 (Origin), RFC 9110 section 8.3 (Content-Type)";
        }
        in originValid : Boolean;
        in authValid : Boolean;
        in mediaTypeValid : Boolean;
        in bodyBytes : Integer;
        in settingsValid : Boolean;
        in profileMatches : Boolean;
        in expectedRevision : Integer;
        in currentRevision : Integer;
        in durableReplaceSucceeded : Boolean;
        return outcome : HttpOutcome =
            if not originValid ? HttpOutcome::forbidden_origin else
            if not authValid ? HttpOutcome::unauthorized else
            if not mediaTypeValid ? HttpOutcome::unsupported_media_type else
            if bodyBytes > profileHttpMaxBytes ? HttpOutcome::request_too_large else
            if not settingsValid ? HttpOutcome::invalid_settings else
            if not profileMatches ? HttpOutcome::wrong_profile else
            if expectedRevision != currentRevision ? HttpOutcome::revision_conflict else
            if currentRevision == maxRevision ? HttpOutcome::revision_exhausted else
            if not durableReplaceSucceeded ? HttpOutcome::storage_unavailable else
            HttpOutcome::ok;
    }
    calc def ResponseBudgetAdmission {
        doc /* Before readiness, the launch encodes the complete HttpProfileRepresentation with
             the effective origin and the largest valid later settings and revision, not only
             the values in the file, and admits the profile only if it fits
             profileHttpMaxBytes. A refused profile gives invalid_profile; an admitted one
             keeps room for every valid later edit. The endpoint identity is never truncated
             or replaced. */
        doc /* The worst case with an empty origin is 2,018 bytes of compact UTF-8: 36-byte
             profile and boot UUIDs, revision maxRevision, standard, a display name of 64
             backslashes, callsign A12345678901, locator RR99XX99, both audio identifiers and
             the CAT endpoint of 256 backslashes each, CAT mode and PTT disabled. The escaped
             origin may therefore take 6,174 bytes. */
        in completeWorstCaseUtf8Bytes : Integer;
        return admitted : Boolean =
            completeWorstCaseUtf8Bytes >= 0 and completeWorstCaseUtf8Bytes <= profileHttpMaxBytes;
    }
    calc def GetDecision {
        in originAbsentOrExact : Boolean;
        in authValid : Boolean;
        return outcome : HttpOutcome = if not originAbsentOrExact ?
            HttpOutcome::forbidden_origin else if not authValid ?
            HttpOutcome::unauthorized else HttpOutcome::ok;
    }
    calc def HttpStatus {
        @FollowsSource { reference = "RFC 9110 section 15"; }
        in outcome : HttpOutcome;
        return status : Integer =
            if outcome == HttpOutcome::ok ? 200 else
            if outcome == HttpOutcome::forbidden_origin
                or outcome == HttpOutcome::wrong_profile ? 403 else
            if outcome == HttpOutcome::unauthorized ? 401 else
            if outcome == HttpOutcome::unsupported_media_type ? 415 else
            if outcome == HttpOutcome::request_too_large ? 413 else
            if outcome == HttpOutcome::invalid_settings ? 400 else
            if outcome == HttpOutcome::storage_unavailable ? 503 else 409;
    }
    metadata audioEndpointConflict : Conflict about HttpOutcome, HttpStatus {
        what = "CL-044-05 states 400 audio_device_not_endpoint for PUT /profile; HttpOutcome "
            + "does not list it and HttpStatus maps an unlisted outcome to 409";
    }
    calc def NextRevision {
        in beforeRevision : Integer;
        in saveOutcome : HttpOutcome;
        return afterRevision : Integer = if saveOutcome == HttpOutcome::ok ?
            beforeRevision + 1 else beforeRevision;
    }

    action def CreateProfile {
        in directoryArgument : String;
        out createdDocument : ProfileDocument[0..1];
        out outcome : StartupOutcome;
        doc /* --create-profile <directory> is the sole command; a relative directory resolves
             from the working directory. The parent must exist and the target must not, also
             when it would be empty; the target is never overwritten. */
        doc /* Creation writes profile.json with the defaults of ProfileDocument, Settings,
             Endpoint, AudioSelection and ControlSelection, a fresh UUID v4 and revision 0, and
             exits created without a listener or a browser. */
        doc /* An unknown, duplicate or combined argument gives invalid_runtime_configuration;
             an existing target, an absent parent or a storage failure gives
             resource_unavailable. A launch never falls back to creation. */
    }
    action def LaunchSelectedProfile {
        in directoryArgument : String;
        in runtime : RuntimeInputs;
        out selected : ProfileDocument[0..1];
        out bootIdentity : String[0..1];
        out effectiveBrowserOrigin : String[0..1];
        out outcome : StartupOutcome;
        doc /* --profile <directory> resolves and canonicalizes the directory from the working
             directory. An unknown or duplicate argument, --create-profile beside it, or a
             present WSTX_BIND or WSTX_ORIGIN gives invalid_runtime_configuration. */
        doc /* A missing or unreadable directory or profile.json gives resource_unavailable. */
        doc /* Malformed UTF-8 or JSON, a duplicate, extra or missing key, a wrong type or
             domain, a file over profileFileMaxBytes, an invalid UUID, bind port 0 or 65536, a
             malformed origin or an origin port other than the bind port gives
             invalid_profile; so does a NativeProfileDocument with an explicit null or an
             unknown key. */
        doc /* A schema_version other than 1 and 2, or schema 2 without the key native, gives
             unsupported_schema; a schema 1 document naming native_flex gives
             unsupported_connection_type. */
        doc /* The profile is validated before any request is accepted. */
        doc /* The launch takes exclusive ownership of the directory and of the profile UUID for
             the account, held by the operating system for its lifetime: the same directory
             through any alias, or a copy of an owned UUID, gives profile_in_use; a denied lock
             gives resource_unavailable. */
        doc /* An incomplete TLS pair, TLS without token, a token without TLS, a token that is
             not 32..128 ASCII letters and digits, insecure or incomplete remote inputs, or a
             saved origin whose scheme differs from the runtime TLS gives
             invalid_runtime_configuration; an absent, unreadable or invalid certificate or key
             gives resource_unavailable. */
        doc /* ResponseBudgetAdmission runs for the effective origin before readiness. */
        doc /* An occupied port gives endpoint_in_use; another failure of an operating-system
             resource gives resource_unavailable. Each single fault gives exactly its
             outcome. */
        doc /* A refused launch exits nonzero without readiness, browser, attachment, file
             rewrite or disruption of another process. */
        doc /* Ready, the launch takes a fresh UUID v4 boot ID that is not persisted and reports
             the effective browser origin and the selected UUID and name, no secret; it opens
             no browser. Readiness comes within readinessDeadlineSeconds, and the number of
             profiles running at once has no fixed bound. */
        doc /* Without arguments the station keeps the environment mode of WstxStationProtocol
             and wstx.v1: GET and PUT /profile answer 404, and no profile is created, migrated
             or searched. */
    }
    action def SaveSelectedProfile {
        in request : SaveProfile;
        in beforeDocument : ProfileDocument;
        out afterDocument : ProfileDocument;
        out outcome : HttpOutcome;
        assert constraint identityStable { afterDocument.profile_id == beforeDocument.profile_id }
        assert constraint revisionEffect {
            afterDocument.revision == (if outcome == HttpOutcome::ok ?
                beforeDocument.revision + 1 else beforeDocument.revision)
        }
        assert constraint failedSettingsUnchanged {
            outcome != HttpOutcome::ok implies afterDocument.settings == beforeDocument.settings
        }
        doc /* The web adapter authenticates, checks the Origin and decodes the request; the
             station calls only its selected profile. */
        doc /* Saves are serialized: the expected revision is checked again with the
             whole-settings validation and the write. A competing stale writer neither merges
             nor overwrites. */
        doc /* The API edits no identity, endpoint or connection type. */
        doc /* The commit point is the replacement of profile.json. Before it the old bytes and
             revision stay authoritative, and a failure gives storage_unavailable with the old
             file, the old state in memory and the server available. After it the complete new
             document is authoritative with revision + 1, and only then is the save
             acknowledged with 200. */
        doc /* A GET during a save sees the complete old or the complete new revision. A lost
             response is resolved by a GET, never by an automatic replay. */
        doc /* A save never acknowledges a partial write, selects a path, activates a driver or
             merges silently. */
        doc /* A PUT to a native profile naming an audio device, CAT or PTT, or radio settings,
             gives invalid_settings with that field. */
    }
    action def RecoverOrStopProfile {
        in selected : ProfileDocument;
        out outcome : StartupOutcome;
        doc /* Stop releases the listener and the locks; a crash releases the operating-system
             ownership too. A marker file alone owns no directory and no UUID, so a killed
             process can start again. */
        doc /* A restart reads only profile.json: a leftover temporary file is ignored and never
             promoted. A missing, corrupt or future file fails without reset, rewrite or copy
             from another profile. */
        doc /* The operator restores a known complete copy while the profile is stopped, or
             creates a new profile. A write to the file by another program while it is owned is
             unsupported. An endpoint edited while stopped is validated at the next launch; an
             edit of the UUID is unsupported. */
        doc /* An acknowledged save survives a process restart and an ordered restart of the
             operating system; after a reboot the operator starts the profile. There is no
             automatic backup selection, migration, autostart or device discovery, and no
             guarantee against a hostile user or against arbitrary power or storage failure. */
        doc /* The other profiles' processes, settings and sessions stay usable: profiles share
             no lifecycle. */
    }

    state def ProfileLifecycle {
        doc /* The lifecycle of one selected profile process. starting runs
             LaunchSelectedProfile and saving runs SaveSelectedProfile; a save returns to
             running with the new or the old revision. Stop or crash releases ownership and
             listener; a refused launch never becomes ready. A crash during the replacement
             leaves the complete old or the complete new document. */
        attribute startRequested : Boolean;
        attribute stopOrCrash : Boolean;
        attribute launchFinished : Boolean;
        attribute launchOutcome : StartupOutcome;
        attribute saveRequested : Boolean;
        attribute saveFinished : Boolean;
        entry; then stopped;
        state stopped;
        state starting;
        state running;
        state saving;
        state rejected;
        transition startProfile first stopped if startRequested then starting;
        transition started first starting
            if launchFinished and launchOutcome == StartupOutcome::ready then running;
        transition refused first starting
            if launchFinished and launchOutcome != StartupOutcome::ready then rejected;
        transition requestSave first running if saveRequested then saving;
        transition completeSave first saving if saveFinished then running;
        transition stopRunning first running if stopOrCrash then stopped;
        transition stopSaving first saving if stopOrCrash then stopped;
        transition stopStarting first starting if stopOrCrash then stopped;
        transition exitRejected first rejected then stopped;
    }

    action createProfile : CreateProfile;
    action launchProfile : LaunchSelectedProfile;
    action saveProfile : SaveSelectedProfile;
    action stopOrRecover : RecoverOrStopProfile;
    dependency launchOwner from launchProfile
        to WstxArchitecture::StationProcess::profile;
    dependency saveOwner from saveProfile
        to WstxArchitecture::StationProcess::profile;
    dependency stationValidationOwner from saveProfile
        to WstxArchitecture::StationProcess::station;
    dependency createOwner from createProfile to WstxProfiles::PersistedProfile;
    dependency lifecycleOwner from stopOrRecover
        to WstxArchitecture::Backend::stations;
    dependency internalRequestRefinement from SaveProfile to WstxProfileAccess::ProfileRequest;
    dependency externalRequestRefinement from HttpProfilePut
        to WstxStationCommands::StationRequest;
    satisfy 'CL-005-01' by launchProfile;
    satisfy 'CL-005-02' by saveProfile;
    satisfy 'CL-005-04' by launchProfile;

    requirement 'CL-005-01' {
        doc /* Each selected profile MUST own exactly one station process and listener, and the
             number of profiles running at once MUST have no fixed limit. */
        @Status { build = ImplementationState::implemented; }
    }
    dependency CL_005_01_to_FR_022 from 'CL-005-01' to 'FR-022';
    requirement 'CL-005-04' {
        doc /* Launch and save MUST end with an explicit StartupOutcome or HttpOutcome on
             contested ownership, invalid storage, an occupied endpoint or an unavailable
             resource, without replacing the saved configuration or disrupting a running
             profile. */
        @Status { build = ImplementationState::implemented; }
    }
    dependency CL_005_04_to_FR_016 from 'CL-005-04' to 'FR-016';
    dependency CL_005_04_to_FR_021 from 'CL-005-04' to 'FR-021';
    dependency CL_005_04_to_FR_022 from 'CL-005-04' to 'FR-022';
    requirement 'CL-005-05' {
        doc /* The profile MUST persist its audio and control selections independently of each
             other, with standard audio and CAT and PTT disabled by default and without
             claiming that a device is available; a native FlexRadio profile MUST be a
             NativeProfileDocument chosen at creation. */
        @Status { build = ImplementationState::implemented; }
        @ImplementedIn { module = "server/src/profile.rs; client/app.js"; }
    }
    dependency CL_005_05_to_FR_001 from 'CL-005-05' to 'FR-001';
    dependency CL_005_05_to_FR_022 from 'CL-005-05' to 'FR-022';

    verification 'TC-022-002' {
        doc /* TC-022-002 — Persistence and independent restart
             Setup: four profiles from the fixture table, each in its own directory: UUID
             00000000-0000-4000-8000-00000000000i, Station i, TESTi, JN47AA, revision 0,
             standard, fixture-input-i and fixture-output-i, control disabled, null, disabled
             (i = 1..4). The operational windows are HTTPS with selected grants, with
             plaintext numeric loopback for compatibility. Test-build checkpoints sit on the
             real save path.
             (a) --create-profile writes exactly the defaults of ProfileDocument, Settings,
                 Endpoint, AudioSelection and ControlSelection, with a fresh UUID v4 and
                 revision 0, and opens no listener. An existing target, empty or not, or an
                 absent parent gives resource_unavailable.
             (b) Four acknowledged saves survive restart and kill, each with a fresh boot ID.
                 A leftover temporary file and a leftover marker are ignored. No restart of
                 the operating system is claimed.
             (c) A file of exactly profileFileMaxBytes loads; one byte more gives
                 invalid_profile. Malformed UTF-8 or JSON, a duplicate, unknown or missing
                 key, a bad UUID, or port 0 or 65536 gives invalid_profile; a missing file
                 gives resource_unavailable; schema 0, or schema 2 without native, gives
                 unsupported_schema; schema 1 naming native_flex gives
                 unsupported_connection_type. The file bytes stay unchanged in every case, and
                 the restored bytes launch again.
             (d) A denied write gives 503 storage_unavailable and keeps the old state. A crash
                 before or after the replacement leaves the complete old or the complete new
                 document.
             (e) A lost 200 reply: only one PUT is sent, a later GET returns the committed
                 revision, and Save stays disabled until an explicit reload; a failed reload
                 keeps it disabled. This browser condition is kept for the interaction it
                 proves.
             (f) The response budget, over numeric loopback with the saved origin as the
                 Origin header and no external DNS: the empty-origin worst case is 2,018
                 bytes; an origin sized so that the complete representation is exactly
                 profileHttpMaxBytes launches and the bodies fit, including a save from
                 maxRevision - 1 to maxRevision; one more origin byte, or a 9,000-character
                 hostname, gives invalid_profile before readiness without a file rewrite.
             (g) A relative path from another working directory, aliases, invalid arguments,
                 and WSTX_BIND or WSTX_ORIGIN each give their mapped outcome.
             Oracle: independent expected fields and hashes, never the candidate's helpers.
             No power-loss durability or migration from WSJT-X is claimed.
             2 — Isolated automated tests; Windows PC, disposable storage, N real processes
             and windows. */
        @Automation { run = AutomationState::partial; }
        objective {
            verify 'CL-005-02';
            verify 'CL-005-04';
            verify 'CL-005-05';
            verify 'FR-001';
            verify 'FR-016';
            verify 'FR-022';
        }
        @TestedBy { test = "tests/profiles.test.cjs; server/src/profile_tests.rs"; }
    }
    verification 'TC-022-003' {
        doc /* TC-022-003 — Lifecycle, ownership and isolation
             Setup: four running profiles with valid inputs; each fault is applied alone, with
             otherwise valid TLS and token inputs.
             (a) Profile 1 stops and restarts while the other three refresh within
                 WstxSettings::loopbackRefreshDeadlineSeconds and stay unchanged.
                 Profile 1 returns with its UUID and revision and a new boot ID.
             (b) The same path, an alias or a copied UUID gives profile_in_use until the
                 owner exits, whatever the directory's name. An occupied port gives
                 endpoint_in_use.
             (c) Denied storage and an absent, unreadable or invalid TLS file give
                 resource_unavailable; incomplete TLS, an absent or malformed token, a remote
                 plaintext bind, an environment override or a runtime scheme mismatch gives
                 invalid_runtime_configuration; a malformed stored origin or a port mismatch
                 gives invalid_profile.
             (d) Each refusal exits non-zero within readinessDeadlineSeconds, with no
                 readiness, no file rewrite and no interruption of the other profiles. After
                 the fault is cleared, launch succeeds.
             (e) Killing the owner releases its lock. A marker alone holds nothing.
             Oracle: the mapped faults and independent hashes.
             2 — Isolated automated tests; Windows PC, N real processes and windows, port
             reservations and controlled resource faults, never exhaustion of the PC. */
        @Automation { run = AutomationState::partial; }
        objective {
            verify 'CL-005-03';
            verify 'CL-005-04';
            verify 'FR-021';
            verify 'FR-022';
        }
        @TestedBy { test = "tests/profiles.test.cjs; server/src/profile_tests.rs"; }
    }
    dependency CL_005_01_verified_by_TC_022_001 from 'CL-005-01' to 'TC-022-001';
    dependency CL_005_04_verified_by_TC_022_002 from 'CL-005-04' to 'TC-022-002';
    dependency CL_005_04_verified_by_TC_022_003 from 'CL-005-04' to 'TC-022-003';
    dependency CL_005_04_verified_by_TC_022_004 from 'CL-005-04' to 'TC-022-004';
    dependency CL_005_05_verified_by_TC_022_001 from 'CL-005-05' to 'TC-022-001';
    dependency CL_005_05_verified_by_TC_022_002 from 'CL-005-05' to 'TC-022-002';
    requirement 'CL-005-02' {
        doc /* Stable identity, schema, validated settings, revision and acknowledged saves MUST survive process restart. The browser MUST identify the selected profile and permit the bounded edits below. */
        attribute coverage : ImplementationState = ImplementationState::partial;
        attribute implementation : String = "server/src/profile.rs; client/app.js";
    }
    dependency CL_005_02_to_FR_001 from 'CL-005-02' to 'FR-001';
    dependency CL_005_02_to_FR_016 from 'CL-005-02' to 'FR-016';
    dependency CL_005_02_to_FR_019 from 'CL-005-02' to 'FR-019';
    dependency CL_005_02_to_FR_022 from 'CL-005-02' to 'FR-022';
    requirement 'CL-008-01' {
        doc /* Persist independently selected audio and typed IC-7300 control intent through the existing profile revision/atomic-store boundary; settings never assert device availability. */
        attribute coverage : ImplementationState = ImplementationState::implemented;
        attribute implementation : String = "server/src/audio.rs; server/src/audio/windows.rs; server/src/radio_control/mod.rs; server/src/receive.rs";
    }
    dependency CL_008_01_to_FR_001 from 'CL-008-01' to 'FR-001';
    dependency CL_008_01_to_FR_002 from 'CL-008-01' to 'FR-002';
    dependency CL_008_01_to_FR_009 from 'CL-008-01' to 'FR-009';
    dependency CL_008_01_to_FR_022 from 'CL-008-01' to 'FR-022';
    verification 'TC-002-001' {
        doc /* TC-002-001 — Canonical live audio
             CL-008-01, CL-008-02, CL-008-03
             Inject independently timed mono/stereo native float/PCM packets, silence flags, arbitrary splits, exact queue limits/one-over, gaps, timestamp errors, DATA_DISCONTINUITY flags on contiguous positions with QPC steps inside and just outside the2 ms bound, missing devices and cancellation into actual capture/converter boundaries. Generate analytic tones/impulses and rational frame maps independently.
             Channel0/normalization/finite-value rules, exact rational counts and block partition invariance within2e-5, group-delay alignment within one canonical frame, passband0.1dB/stopband60dB, bounded storage and no gap-crossing/fake silence. A contiguous flag within2 ms of the QPC timeline keeps one epoch and gap-free frames; beyond2 ms it is unknown loss; every unknown-loss epoch names its trigger. Canonical recordings unchanged. Cancel release<=250ms except explicit failed-close state; capture never invokes CAT.
             2 — Isolated automated tests; Windows development PC, actual candidate modules and independent device/clock fixtures. */
        attribute automation : AutomationState = AutomationState::partial;
        objective {
            verify 'CL-008-01';
            verify 'CL-008-02';
            verify 'CL-008-03';
        }
        attribute executable : String = "server/tests/audio_contract.rs; server/tests/audio_receive.rs; server/tests/receive_integration.rs; server/tests/source_contract.rs; server/src/audio.rs";
    }
    verification 'TC-009-001' {
        doc /* TC-009-001 — Typed radio control
             CL-008-01, CL-008-03, CL-008-04, CL-008-06
             Feed manually derived CI-V query/set/ACK/NG/readback bytes through fragmented, malformed, echoed, foreign, stale, flooded and boundary-sized transport fixtures. Test auto-baud order/deadlines, invalid catalogue/URI, physical alias conflicts and cancellation before/after send.
             Exact bytes/readback semantics; no bytes for invalid/raw/TX requests; no deadline renewal/in-flight exchange retry/write replay; one owner/no queue; every cap and one-over; missing/busy/failed-close state truthful; two processes cannot own the same physical resource.
             2 — Isolated automated tests; Windows development PC, compiled control service and independent protocol/serial emulator. */
        attribute automation : AutomationState = AutomationState::partial;
        objective {
            verify 'CL-008-01';
            verify 'CL-008-03';
            verify 'CL-008-04';
            verify 'CL-008-06';
        }
        attribute executable : String = "server/tests/radio_control.rs";
        attribute method : String = "manual";
    }
    verification 'TC-022-001' {
        doc /* #### TC-022-001 — Variable independent servers and browser windows

             **Promises:** FR-001, FR-019, FR-021, FR-022; CL-005-01, CL-005-02, CL-005-03,
             CL-005-05. **Level:** 2 — isolated automated tests.
             **Where:** Windows PC, N real server processes and separate real browser windows.

             **Setup partition:** Operational browser windows and save/readiness regressions
             use four saved HTTPS localhost endpoints and legitimate selected grants in one
             browser context, per WstxSettings::IndependentVerification. Plaintext trusted
             numeric-loopback HTTP/launch compatibility is a separate mandatory companion,
             not an operational configuration GUI or Connected/protected-WS prerequisite.

             **Steps:** Launch each table profile with `--profile`; open one window per recorded
             endpoint. Match every visible full UUID, display name, endpoint, boot ID and revision
             to its fixture; require N distinct boot IDs/listeners/PIDs. Refresh every window.
             In window 1 save name `Edited station 1`, audio input `changed-input-1` and CAT endpoint
             `fixture-cat-1`, CAT mode and disabled PTT; retain its output and all other fields.
             Reload/Refresh a second window on profile 1 and all other station windows. Repeat with
             empty audio selections and disabled CAT; save audio alone and control alone.

             **Oracle/outcome:** Only profile 1 advances to the next revision and changes the
             specified fields; every other file and visible identity/settings remains equal to the
             input table. The second window observes the same acknowledged revision on refresh.
             All windows show radio unconfigured and saved device selections not activated. No
             serial/device access is attempted. The native option is visibly reserved/disabled.
             There is no four-entry ceiling. Check the form at desktop width and 360 px: identity,
             errors and Save remain readable/reachable with keyboard input.

             **Plaintext API companion:** With trusted numeric loopback, no cookie and the
             exact saved Origin where supplied, require GET/valid durable PUT200, identical
             JSON keys/UUID/revision/settings/size expectations, ordered errors/domain/byte
             boundaries, unchanged file bytes on rejection and exact durable fields on success.
             Retain the complete validation matrix below in this companion AND current-grant
             HTTPS protected ordered checks; no auth bypass or omitted existing variant.
             Plaintext auth-v1/protected WS/native remain denied, never operational readiness.

             **Validation variants:** In one isolated profile, submit every editable field's empty,
             maximum and one-beyond-maximum value from 4.2, controls/newlines, malformed callsign/
             locator, wrong JSON types, invalid CAT/PTT combinations and an attempted native selection.
             Empty callsign/locator and nullable audio are valid; empty display name/opaque identifier
             are invalid. Test literal markup in a valid display name and require visible text without
             HTML execution. In particular, save display name `<img src=x onerror=alert(1)>` and
             audio identifier `<script>alert(1)</script>`; require their exact literal text in the
             appropriate page/form fields, no injected element, and no script/dialog execution.
             Exercise wrong profile ID, stale revision, duplicate/extra/missing fields,
             invalid JSON, unsupported media type and exact 8,192/8,193-byte bodies per 12.5 (pad
             an otherwise valid JSON object with whitespace). Each rejected save
             leaves memory/revision/file unchanged and shows its field/error outcome; valid boundary
             saves persist exactly. Revision exhaustion refuses another save. Test a second window
             saving from an old revision: one save wins, one receives 409, no silent merge/lost update.
             Also hold an announced revision's GET response, begin and hold a PUT, then release the GET while the
             save remains pending. Save stays disabled and even a repeated form submission sends
             no second PUT. Release the PUT: exactly one revision advances, editable controls and
             Save recover their usable state, and permanently read-only controls remain disabled.
             Repeat with the opposite response order on an unchanged revision-0 station: hold the
             announced revision's GET response, complete the PUT, whose 200 reply is the revision-1
             snapshot (CL-073-01, no follow-up GET), then release the old response. Visible revision, saved fields and acknowledged-save feedback remain at
             revision 1. A changed boot identity still permits restart/recovery resynchronization.

             **Automation coverage:** Existing companions retain the delivered profile,
             domain/API and form-ordering subset. Operational HTTPS/grant fixture conversion
             and complete separate plaintext plus protected-HTTPS validation coverage remain
             pending; the expanded case is partial, without discarding existing assertions. */
        attribute automation : AutomationState = AutomationState::partial;
        objective {
            verify 'CL-005-01';
            verify 'CL-005-02';
            verify 'CL-005-03';
            verify 'CL-005-05';
            verify 'FR-001';
            verify 'FR-019';
            verify 'FR-021';
            verify 'FR-022';
        }
        attribute executable : String = "tests/profiles.test.cjs; server/src/profile_tests.rs";
    }
    verification 'TC-022-005' {
        doc /* #### TC-022-005 — Status readiness independent of settings transport

             Proves CL-005-02, CL-005-03 and CL-006-04. Level 2, automated Windows real Chromium/server
             fixture in tests/profiles.test.cjs, using the common four-process operational
             HTTPS/grant fixture before each relevant protected socket. Preserve separate
             plaintext HTTP/launch compatibility; auth setup requests do not count as profile
             GETs and auth status cannot replace correlated WS status.
             On an established socket a Refresh sends no GET /profile (#10 profile.state); an
             independent save makes the station announce the revision and the browser reads once.
             Hold that GET behind a controlled barrier, click Refresh,
             observe its actual correlated WebSocket status and require changed visible updated plus
             enabled Refresh within 2 seconds before releasing HTTP. Repeat Refresh while held: it adds no GET; a second independent save while held starts no parallel read, and
             one follow-up eventually obtains that newer
             revision without overwriting dirty input. On a fresh socket hold initial GET: Connected,
             station-ready and optional display remain withheld until validated success. Close that
             socket with HTTP held, establish a replacement, then release the old response: it cannot
             restore Connected, replace the newer profile snapshot or overwrite its form. Fail the
             initial/background GET separately: visible failure/stale, no false configuration success.
             Oracles are these independent canonical timing/identity expectations, real WS traffic and independently
             prepared profile revisions; barrier release happens only after the status assertion.

             **Automation coverage:** Existing companions retain the delivered legacy
             socket/settings-readiness subset. The operational HTTPS/grant fixture conversion
             remains pending; the expanded case is partial, with every existing timing,
             held-response, count and stale-form assertion retained. */
        attribute automation : AutomationState = AutomationState::partial;
        objective {
            verify 'CL-005-02';
            verify 'CL-005-03';
            verify 'CL-006-04';
        }
        attribute executable : String = "tests/profiles.test.cjs";
    }
    dependency CL_005_02_verified_by_TC_022_001 from 'CL-005-02' to 'TC-022-001';
    dependency CL_005_02_verified_by_TC_022_002 from 'CL-005-02' to 'TC-022-002';
    dependency CL_005_02_verified_by_TC_022_005 from 'CL-005-02' to 'TC-022-005';
    dependency CL_008_01_verified_by_TC_002_001 from 'CL-008-01' to 'TC-002-001';
    dependency CL_008_01_verified_by_TC_009_001 from 'CL-008-01' to 'TC-009-001';
    requirement 'CL-044-05' {
        doc /* PUT /profile refuses an audio device that is not a WASAPI endpoint ID: settings.audio.input_device must be a capture endpoint ID {0.0.1.00000000}.{GUID} and settings.audio.output_device a render endpoint ID {0.0.0.00000000}.{GUID} (lower- or upper-case hex), else 400 audio_device_not_endpoint with the field; null stays allowed. At station start an existing profile whose device entry is not an endpoint ID is migrated: when exactly one active endpoint of that flow has exactly that friendly name, the entry is replaced by its ID and the profile saved (revision + 1); otherwise it is kept and the startup log names the field and the reason (not_found or ambiguous). Loading a profile never fails because of a device entry. */
        attribute coverage : ImplementationState = ImplementationState::implemented;
        attribute implementation : String = "server/src/profile.rs; server/src/main.rs; server/src/radio_control/setup.rs; server/src/audio/windows.rs";
    }
    dependency CL_044_05_to_FR_001 from 'CL-044-05' to 'FR-001';
    dependency CL_044_05_to_FR_002 from 'CL-044-05' to 'FR-002';
    dependency CL_044_05_to_FR_016 from 'CL-044-05' to 'FR-016';
    dependency CL_044_05_verified_by_TC_044_002 from 'CL-044-05' to 'TC-044-002';
    dependency CL_044_05_verified_by_TC_044_004 from 'CL-044-05' to 'TC-044-004';
    part def PersistedProfile {
        attribute configuration : WstxProfileAccess::ProfileDocument;
        doc /* Backend-owned saved configuration uses exactly the canonical profile schema.
             Live operating selection, browser preference and runtime secrets are separate. */
        doc /* Bootstrap/profile owns selection, stable identity, endpoints, exclusive ownership, validation and storage; not DSP or browser state. */
        doc /* Exactly one explicitly selected profile per process owns stable identity,
             configuration, contacts and recordings. WstxProfiles owns its schema,
             persistence, validation and session behaviour. */
        port context : ~ProfileAccess;
        port contacts : ~ProfileAccess;
        port upload : ~RecordingTransfer;
        port recordedSamples : ReceiveSamples;
        part recordings : RecordedSource;
        connection storedUpload connect upload to recordings.upload;
        connection storedSamples connect recordings.samples to recordedSamples;
    }
}
