// Fixture of the model-value readers (TC-DOC-014): the fixture's own unit list. Secs is
// deliberately not on it.
package WstxUnits {
    enum def UnitSuffix {
        doc /* Hz: hertz. MiB: mebibytes. Ms: milliseconds. */
        enum Hz;
        enum MiB;
        enum Ms;
    }
}
